(defun C:tool_katalog_coor ( / MG N TB TBITEM TBS temp)
  (setq mg (vl-catch-all-apply 'vla-Item (list (vla-get-MenuGroups (vlax-get-acad-object)) "ACAD")))
  (setq tbs (vla-get-Toolbars mg))
  (if (vl-catch-all-error-p(setq temp (vl-catch-all-apply 'vla-Item (list tbs "Исходные координаты"))))
    (progn
      (setq tb (vla-Add tbs "Исходные координаты"))
      (setq n 0)
      (foreach x (list ;(list "Найти" "Ищет пункт в базе по имени" "(alert\"Найти\") " (strcat *geo_tools_root_dir* "\\icons\\find.bmp"))
		       (list "Нанести пункты" "Чертит пункты в указаном квадрате" "draw_punkts_by_square " (strcat *geo_tools_root_dir* "\\icons\\draw.bmp"))
		       (list "Вычистить пункты" "Удаляет все блоки пунктов с чертежа" "clear_punkts " (strcat *geo_tools_root_dir* "\\icons\\clear.bmp"))
		       (list "Добавить пункт" "Процедура добавления нового пункта в базу" "add_puncts_in_katalog " (strcat *geo_tools_root_dir* "\\icons\\add.bmp"))
		       (list "Редактировать пункт" "Позволяет отредактировать данные указанного пункта в базе" "edit_punkts_of_katalog " (strcat *geo_tools_root_dir* "\\icons\\edit.bmp"))
		       (list "Удалить пункт" "Удаление указаного (нанесенного) пункта из базы" "del_punkts_of_katalog " (strcat *geo_tools_root_dir* "\\icons\\delete.bmp"))
		       (list "Импорт" "Импортирует пункты из текстового файла" "import_punkts_from_file " (strcat *geo_tools_root_dir* "\\icons\\import.bmp"))
		       (list "Экспорт" "Экспортирует все пункты каталога в текстовый файл" "export_punkts_in_file " (strcat *geo_tools_root_dir* "\\icons\\export.bmp"))
		       (list "Настройки" "Настройки каталога координат" "options_coordinate_katalog " (strcat *geo_tools_root_dir* "\\icons\\properties.bmp"))
		       (list "Статистика" "Статистическая информация" "statistics_katalog_coordinate " (strcat *geo_tools_root_dir* "\\icons\\help.bmp"))
		       )
	(setq tbitem (vla-AddToolbarButton tb n (nth 0 x) (nth 1 x) (nth 2 x)))
	(vla-SetBitmaps tbitem (nth 3 x) (nth 3 x))
	(setq n (1+ n))
	)
      )
    (if (eq (vla-get-Visible temp) :vlax-false)
      (vla-put-Visible temp :vlax-true))
    )
  (princ)
  )
