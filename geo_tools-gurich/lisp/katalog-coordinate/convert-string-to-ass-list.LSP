(defun convert-string-to-ass-list (string / LIST-POINT RESULT)
  (setq list-point (convert-string-to-list-be-delimiter string "|"))
  (if (/= (nth 0 list-point) "")(setq result(append result(list(list "name" (nth 0 list-point))))))
  (if (/=(atof(nth 1 list-point))0)(setq result(append result(list(list "N" (rtos(atof(nth 1 list-point))2 3))))))
  (if (/=(atof(nth 2 list-point))0)(setq result(append result(list(list "E" (rtos(atof(nth 2 list-point))2 3))))))
  (if (/=(atof(nth 3 list-point))0)(setq result(append result(list(list "Z" (rtos(atof(nth 3 list-point))2 3))))))
  (if (/= (nth 4 list-point) "")(setq result(append result(list(list "type" (nth 4 list-point))))))
  (if (/= (nth 5 list-point) "")(setq result(append result(list(list "address" (nth 5 list-point))))))
  (if (/= (nth 6 list-point) "")(setq result(append result(list(list "year" (nth 6 list-point))))))
  (if (/= (nth 7 list-point) "")(setq result(append result(list(list "comment" (nth 7 list-point))))))
  result)
