(defun analisis-string-from-data (string / flag1 flag2 list-string length-string data n result summ-delimetr year list-years)
  (setq list-string (vl-string->list string))
  (setq length-string (length list-string))
  (setq n 0)
  (while (not flag1)
    (if (analisis-kod-by-number (nth n list-string))
      (progn
	(while (not flag2)
	  (setq data (append data (list (nth n list-string))))
	  (setq n (1+ n))
	  (if (not(or (analisis-kod-by-number (nth n list-string))(analisis-kod-by-delimiter (nth n list-string))))
	    (setq flag2 T))
	  (if (or (= n length-string)(> n length-string))(setq flag2 T))
	  )
	(setq summ-delimetr 0)
	(foreach x data
	  (if (analisis-kod-by-delimiter x)(setq summ-delimetr (1+ summ-delimetr)))
	  )
	(if (= summ-delimetr 2) (setq result (append result (list (vl-list->string data)))))
	(setq data nil)
	(setq flag2 nil)
	)
      )
    (setq n (1+ n))
    (if (or (= n length-string)(> n length-string))(setq flag1 T))
    )
  (foreach x result
    (if (setq year (analisis-data-from-year x))
      (setq list-years (append (list year)))
      )
    )
  (apply 'max list-years)
  )
