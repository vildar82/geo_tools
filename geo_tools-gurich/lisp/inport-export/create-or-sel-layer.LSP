(defun create-or-sel-layer (layer-name /)
  ; установка указанного слоя текущим (если такого нет то будет создан если передается nil то будет установлен слой "0")
  (if (not layer-name) (setq layer-name "0"))
  (setvar "nomutt" 1)
  (setvar "cmdecho" 0)
  (if
    (eq(tblsearch "LAYER" layer-name)nil)
    (command "_-LAYER" "с" layer-name "")
    (command "_-LAYER" "_S" layer-name "")
    )
  (setvar "cmdecho" 1)
  (setvar "nomutt" 0)
  (princ)
  )
