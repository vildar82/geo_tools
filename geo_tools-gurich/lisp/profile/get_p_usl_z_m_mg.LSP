(defun get_p_usl_z_m_mg ( stroka / p text); запрос указания точки с возможностью изменить МВ, МГ или/и условный горизонт
  (while (not (eq 'LIST (type p)))
    (setq mv (file_dat_r_g_w "r" "mv" nil))
    (setq mg (file_dat_r_g_w "r" "mg" nil))
    (setq usl_z (file_dat_r_g_w "r" "usl_z" nil))
    (princ)
    (princ "\nМасштабВ 1:")
    (princ (rtos mv 2 0))
    (princ " МасштабГ 1:")
    (princ (rtos mg 2 0))
    (princ " Отметка условного горизонта: ")
    (princ (rtos usl_z 2 2))
    (princ "м")
    (initget "МВ МГ Условный ВСЕ" 1)(setq p (getpoint(strcat stroka "[МВ/МГ/Условный горизонт/ВСЕ]: ")))
    (cond
      ((= p "МВ")
       (setq mv (file_dat_r_g_w "g" "mv" nil)))
      ((= p "МГ")
       (setq mg (file_dat_r_g_w "g" "mg" nil)))
      ((= p "Условный")
       (setq usl_z (file_dat_r_g_w "g" "usl_z" nil)))
      ((= p "ВСЕ")
       (setq mv (file_dat_r_g_w "g" "mv" nil))
       (setq mg (file_dat_r_g_w "g" "mg" nil))
       (setq usl_z (file_dat_r_g_w "g" "usl_z" nil))
       )
      ))
  p)
