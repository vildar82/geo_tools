(defun draw_profil_downgrade (q_chek_v_pr q_sel_v_pr t0! mg 2Dpline /
			      t1_draw_uklon t2_draw_uklon ht styl pro! n_00 spisokv t0 p p1 p2 n t1 t2 t3 s hs H1 H2 ang t11 t1- t22 t2-)
	 (if (= q_chek_v_pr 1)
	   (cond
	     ((= q_sel_v_pr 0)
	      (setq t1_draw_uklon(mapcar '- t0! (list 0 (/ 105 (/ 1000 mg)))))
	      (setq t2_draw_uklon(mapcar '- t0! (list 0 (/ 90 (/ 1000 mg)))))
	      (setq ht (/ 3.5 (/ 1000 mg)))
	      (setq styl (getvar "TEXTSTYLE"))
	      (setq pro! 1)
	      (setq n_00 3)
	      )
	     ((= q_sel_v_pr 1)
	      (setq t1_draw_uklon(mapcar '- t0! (list 0 (/ 105 (/ 1000 mg)))))
	      (setq t2_draw_uklon(mapcar '- t0! (list 0 (/ 90 (/ 1000 mg)))))
	      (setq ht (/ 3.5 (/ 1000 mg)))
	      (setq styl (getvar "TEXTSTYLE"))
	      (setq pro! 1)
	      (setq n_00 3)
	      )
	     ((= q_sel_v_pr 2)
	      (setq t1_draw_uklon(mapcar '- t0! (list 0 (/ 80 (/ 1000 mg)))))
	      (setq t2_draw_uklon(mapcar '- t0! (list 0 (/ 65 (/ 1000 mg)))))
	      (setq ht (/ 3.5 (/ 1000 mg)))
	      (setq styl (getvar "TEXTSTYLE"))
	      (setq pro! 1)
	      (setq n_00 3)
	      )
	     ((= q_sel_v_pr 3)
	      (setq t1_draw_uklon(mapcar '- t0! (list 0 (/ 95 (/ 1000 mg)))))
	      (setq t2_draw_uklon(mapcar '- t0! (list 0 (/ 80 (/ 1000 mg)))))
	      (setq ht (/ 3.5 (/ 1000 mg)))
	      (setq styl (getvar "TEXTSTYLE"))
	      (setq pro! 1)
	      (setq n_00 3)
	      )
	     ((= q_sel_v_pr 4)
	      (setq t1_draw_uklon(mapcar '- t0! (list 0 (/ 105 (/ 1000 mg)))))
	      (setq t2_draw_uklon(mapcar '- t0! (list 0 (/ 95 (/ 1000 mg)))))
	      (setq ht (/ 2.5 (/ 1000 mg)))
	      (setq styl (getvar "TEXTSTYLE"))
	      (setq pro! 1000)
	      (setq n_00 1)
	      )
	     ((= q_sel_v_pr 5)
	      (setq t1_draw_uklon(mapcar '- t0! (list 0 (/ 105 (/ 1000 mg)))))
	      (setq t2_draw_uklon(mapcar '- t0! (list 0 (/ 90 (/ 1000 mg)))))
	      (setq ht (/ 3.5 (/ 1000 mg)))
	      (setq styl (getvar "TEXTSTYLE"))
	      (setq pro! 1)
	      (setq n_00 3)
	      )
	     )
	   (progn
	     (initget)(setq t1_draw_uklon(getpoint "\nУкажи нижнюю линию строки уклонов: "))
	     (initget)(setq t2_draw_uklon(getpoint "\nУкажи верхнюю линию строки уклонов: "))
	     (setq ht (/ 3.5 (/ 1000 mg)))
	     (cond
	       ((= q_sel_uklon 0)
		(setq styl (getvar "TEXTSTYLE"))
		(setq pro! 1)
		(setq n_00 3)
		)
	       ((= q_sel_uklon 1)
		(setq styl (getvar "TEXTSTYLE"))
		(setq pro! 1000)
		(setq n_00 1)
		)
	       )
	     )
	   )
	 (setq spisokv (extract_coord_lwpolyline (entget 2Dpline)))
	 (setq n (1- (length spisokv)))
	 (setq t0 t0!)
	 (repeat n
	   (setq p1 (car spisokv))
	   (setq spisokv (cdr spisokv))
	   (setq p2 (car spisokv))
	   (if
	     (/= (- (nth 0 p1) (nth 0 p2)) 0)
	     (progn
	       (setq hs (- (nth 1 t2_draw_uklon)(nth 1 t1_draw_uklon)))
	       (setq s (- (nth 0 p2) (nth 0 p1)))
	       (setq pro(rtos (abs(*(/ (* (- (nth 1 p1) (nth 1 p2))(/ (* mv (/ 1000 mg)) 1000)) (- (nth 0 p1) (nth 0 p2))) pro!)) 2 n_00))
	       (setq t1 (list (nth 0 p1)(nth 1 t1_draw_uklon)))
	       (setq t2 (list (nth 0 p2)(nth 1 t1_draw_uklon)))
	       (setq H1 (nth 1 p1))
	       (setq H2 (nth 1 p2))
	       (setq t11 (mapcar '+ (list(nth 0 p1)(nth 1 t1_draw_uklon)) (list 0 hs)))
	       (setq t1- (mapcar '+ (list(nth 0 p1)(nth 1 t1_draw_uklon)) (list 0 (/ hs 2))))
	       (setq t22 (mapcar '+ (list(nth 0 p2)(nth 1 t1_draw_uklon)) (list 0 hs)))
	       (setq t2- (mapcar '+ (list(nth 0 p2)(nth 1 t1_draw_uklon)) (list 0 (/ hs 2))))
	       (cond
		 ((= H1 H2); -
		  (entmake (list '(0 . "LINE") '(6 . "Continuous") (append '(10) t1-) (append '(11) t2-)))
		  (if
		    (>
		      (+ (/ 1.6 (/ 1000 mg))(/ (* 1.6 (/ 2 3)) (/ 1000 mg)))
		      (distance t1- t2-)); условие
		    (progn
		      (setq t3 (mapcar '+ t11 (list (/(distance t1 t2)2) (/ (distance t1- t11) -4) )))
		      (draw_mleader_vla model_spece "0.0"(/ 2.5 (/ 1000 mg)) t3(mapcar '+ t3 (list (/ 2 (/ 1000 mg)) (/ 7 (/ 1000 mg)))))
		      )
		    (progn
		      (if
			(< (+(calculation_str_long_be_h_stile "0.0" ht styl)(/ (* 1.6(/ 2 3)) (/ 1000 mg))) (distance t1- t2-))
			(progn
			  (setq ht (/ 3.5 (/ 1000 mg)))
			  (setq ang 0)
			  )
			(progn
			  (setq ang (/ pi 2))
			  (if
			    (< (+(/ 3.5 (/ 1000 mg))(/ (* 3.5 0.6) (/ 1000 mg)))(distance t1- t2-))
			    (setq ht (/ 3.5 (/ 1000 mg)))
			    (setq ht (* (distance t1- t2-) 0.6))
			    )
			  )
			); if
		      (entmake (list '(0 . "TEXT")
				     (cons 10 t1)
				     '(72 . 4)
				     (cons 11 (mapcar '+ t1- (list (/(distance t1- t2-)2) (/ (distance t1 t1-) 2) )))
				     (cons 40 ht)
				     (cons 50 ang)
				     (cons 1 "0.0")
				     (cons 7 styl)
				     )
			       )
		      ); progn
		    ); if
		  (if
		    (>
		      (+ (/ 1.6 (/ 1000 mg))(/ (* 1.6 (/ 2 3)) (/ 1000 mg)))
		      (distance t1 t2)); условие
		    (progn
		      (setq t3 (mapcar '+ t1 (list (/(distance t1 t2)2) (/ (distance t1 t1-) 4) )))
		      (draw_mleader_vla model_spece (rtos S 2 2)(/ 2.5 (/ 1000 mg)) t3(mapcar '+ t3 (list (/ 2 (/ 1000 mg)) (/ -7 (/ 1000 mg)))))
		      )
		    (progn
		      (if
			(< (+(calculation_str_long_be_h_stile (rtos S 2 2) ht styl)(/ (* 1.6(/ 2 3)) (/ 1000 mg))) (distance t1 t2))
			(progn
			  (setq ht (/ 3.5 (/ 1000 mg)))
			  (setq ang 0)
			  )
			(progn
			  (setq ang (/ pi 2))
			  (if
			    (< (+(/ 3.5 (/ 1000 mg))(/ (* 3.5 0.6) (/ 1000 mg)))(distance t1 t2))
			    (setq ht (/ 3.5 (/ 1000 mg)))
			    (setq ht (* (distance t1 t2) 0.6))
			    )
			  )
			); if
		      (entmake (list '(0 . "TEXT")
				     (cons 10 t1)
				     '(72 . 4)
				     (cons 11 (mapcar '+ t1 (list (/(distance t1 t2)2) (/ (distance t1 t1-) 2) )))
				     (cons 40 ht)
				     (cons 50 ang)
				     (cons 1 (rtos S 2 2))
				     (cons 7 styl)
				     )
			       )
		      ); progn
		    ); if
		  )
		 ((> H1 H2); \
		  (entmake (list '(0 . "LINE") '(6 . "Continuous") (cons 10 t11) (cons 11 t2)))
		  (if (>(calculation_h_text_in_triang t1 t11 t2 (calculation_text_ratio_h_for_dlin (rtos S 2 2) ht styl))
			(calculation_h_text_in_triang t1 t2 t11 (calculation_text_ratio_h_for_dlin (rtos S 2 2) ht styl))
			)
		    (cond
		      ((> (*(calculation_h_text_in_triang t1 t11 t2 (calculation_text_ratio_h_for_dlin (rtos S 2 2) ht styl)) 0.8) (/ 3.5 (/ 1000 mg)))
		       (entmake (list '(0 . "TEXT")  '(72 . 0) '(73 . 0)
				      (cons 10 (mapcar '+ t1 (list (/(/ 3.5 (/ 1000 mg))3) (/(/ 3.5 (/ 1000 mg))3) )))
				      (cons 40 (/ 3.5 (/ 1000 mg)))
				      (cons 50 0)
				      (cons 1 (rtos S 2 2)) (cons 7 styl)))
		       )
		      ((< (*(calculation_h_text_in_triang t1 t11 t2 (calculation_text_ratio_h_for_dlin (rtos S 2 2) ht styl)) 0.8) (/ 1.6 (/ 1000 mg)))
		       (setq t3 (mapcar '+ t1 (list (/(distance t1 t2)2) (/ 1 (/ 1000 mg)) )))
		       (draw_mleader_vla model_spece (rtos S 2 2)(/ 2.5 (/ 1000 mg)) t3(mapcar '+ t3 (list (/ 2 (/ 1000 mg)) (/ -7 (/ 1000 mg)))))
		       )
		      (T
		       (entmake (list '(0 . "TEXT")  '(72 . 0) '(73 . 0)
				      (cons 10 (mapcar '+ t1 (list
							       (/(*(calculation_h_text_in_triang t1 t11 t2 (calculation_text_ratio_h_for_dlin (rtos S 2 2) ht styl)) 0.8)3)
							       (/(*(calculation_h_text_in_triang t1 t11 t2 (calculation_text_ratio_h_for_dlin (rtos S 2 2) ht styl)) 0.8)3)
							       )))
				      (cons 40 (*(calculation_h_text_in_triang t1 t11 t2 (calculation_text_ratio_h_for_dlin (rtos S 2 2) ht styl)) 0.8))
				      (cons 50 0)
				      (cons 1 (rtos S 2 2)) (cons 7 styl)))
		       )
		      )
		    (cond
		      ((> (*(calculation_h_text_in_triang t1 t2 t11 (calculation_text_ratio_h_for_dlin (rtos S 2 2) ht styl)) 0.8) (/ 3.5 (/ 1000 mg)))
		       (entmake (list '(0 . "TEXT") (cons 10 t1) '(72 . 0) '(73 . 3)
				      (cons 11 (mapcar '+ t1 (list (/(/ 3.5 (/ 1000 mg))3) (/(/ 3.5 (/ 1000 mg))3) )))
				      (cons 40 (/ 3.5 (/ 1000 mg)))
				      (cons 50 (/ pi 2))
				      (cons 1 (rtos S 2 2)) (cons 7 styl)))
		       )
		      ((< (*(calculation_h_text_in_triang t1 t2 t11 (calculation_text_ratio_h_for_dlin (rtos S 2 2) ht styl)) 0.8) (/ 1.6 (/ 1000 mg)))
		       
		       (setq t3 (mapcar '+ t1 (list (/(distance t1 t2)2) (/ 1 (/ 1000 mg)) )))
		       (draw_mleader_vla model_spece (rtos S 2 2)(/ 2.5 (/ 1000 mg)) t3(mapcar '+ t3 (list (/ 2 (/ 1000 mg)) (/ -7 (/ 1000 mg)))))
		       )
		      (T
		       (entmake (list '(0 . "TEXT") (cons 10 t1) '(72 . 0) '(73 . 3)
				      (cons 11 (mapcar '+ t1 (list
							       (/(*(calculation_h_text_in_triang t1 t2 t11 (calculation_text_ratio_h_for_dlin (rtos S 2 2) ht styl)) 0.8)3)
							       (/(*(calculation_h_text_in_triang t1 t2 t11 (calculation_text_ratio_h_for_dlin (rtos S 2 2) ht styl)) 0.8)3)
							       )))
				      (cons 40 (*(calculation_h_text_in_triang t1 t2 t11 (calculation_text_ratio_h_for_dlin (rtos S 2 2) ht styl)) 0.8))
				      (cons 50 (/ pi 2))
				      (cons 1 (rtos S 2 2)) (cons 7 styl)))
		       )
		      )
		    )
		  (if (>(calculation_h_text_in_triang t22 t2 t11 (calculation_text_ratio_h_for_dlin pro ht styl))
			(calculation_h_text_in_triang t22 t11 t2 (calculation_text_ratio_h_for_dlin pro ht styl))
			)
		    (cond
		      ((> (*(calculation_h_text_in_triang t22 t2 t11 (calculation_text_ratio_h_for_dlin pro ht styl)) 0.8) (/ 3.5 (/ 1000 mg)))
		       (entmake (list '(0 . "TEXT") (cons 10 t1) '(72 . 2) '(73 . 3)
				      (cons 11 (mapcar '- t22 (list (/(/ 3.5 (/ 1000 mg))3) (/(/ 3.5 (/ 1000 mg))3) )))
				      (cons 40 (/ 3.5 (/ 1000 mg)))
				      (cons 50 0)
				      (cons 1 pro) (cons 7 styl)))
		       )
		      ((< (*(calculation_h_text_in_triang t22 t2 t11 (calculation_text_ratio_h_for_dlin pro ht styl)) 0.8) (/ 1.6 (/ 1000 mg)))
		       (setq t3 (mapcar '- t22 (list (/(distance t1 t2)2) (/ 1 (/ 1000 mg)) )))
		       (draw_mleader_vla model_spece pro(/ 2.5 (/ 1000 mg)) t3(mapcar '+ t3 (list (/ 2 (/ 1000 mg)) (/ 7 (/ 1000 mg)))))
		       )
		      (T
		       (entmake (list '(0 . "TEXT") (cons 10 t1) '(72 . 2) '(73 . 3)
				      (cons 11 (mapcar '- t22 (list
								(/(*(calculation_h_text_in_triang t22 t2 t11 (calculation_text_ratio_h_for_dlin pro ht styl)) 0.8)3)
								(/(*(calculation_h_text_in_triang t22 t2 t11 (calculation_text_ratio_h_for_dlin pro ht styl)) 0.8)3)
								)))
				      (cons 40 (*(calculation_h_text_in_triang t22 t2 t11 (calculation_text_ratio_h_for_dlin pro ht styl)) 0.8))
				      (cons 50 0)
				      (cons 1 pro) (cons 7 styl)))
		       )
		      )
		    (cond
		      ((> (*(calculation_h_text_in_triang t22 t11 t2 (calculation_text_ratio_h_for_dlin pro ht styl)) 0.8) (/ 3.5 (/ 1000 mg)))
		       (entmake (list '(0 . "TEXT") (cons 10 t1) '(72 . 2) '(73 . 0)
				      (cons 11 (mapcar '- t22 (list (/(/ 3.5 (/ 1000 mg))3) (/(/ 3.5 (/ 1000 mg))3) )))
				      (cons 40 (/ 3.5 (/ 1000 mg)))
				      (cons 50 (/ pi 2))
				      (cons 1 pro) (cons 7 styl)))
		       )
		      ((< (*(calculation_h_text_in_triang t22 t11 t2 (calculation_text_ratio_h_for_dlin pro ht styl)) 0.8) (/ 1.6 (/ 1000 mg)))
		       (setq t3 (mapcar '- t22 (list (/(distance t1 t2)2) (/ 1 (/ 1000 mg)) )))
		       (draw_mleader_vla model_spece pro(/ 2.5 (/ 1000 mg)) t3(mapcar '+ t3 (list (/ 2 (/ 1000 mg)) (/ 7 (/ 1000 mg)))))
		       )
		      (T
		       (entmake (list '(0 . "TEXT") (cons 10 t1) '(72 . 2) '(73 . 0)
				      (cons 11 (mapcar '- t22 (list
								(/(*(calculation_h_text_in_triang t22 t11 t2 (calculation_text_ratio_h_for_dlin pro ht styl)) 0.8)3)
								(/(*(calculation_h_text_in_triang t22 t11 t2 (calculation_text_ratio_h_for_dlin pro ht styl)) 0.8)3)
								)))
				      (cons 40 (*(calculation_h_text_in_triang t22 t11 t2 (calculation_text_ratio_h_for_dlin pro ht styl)) 0.8))
				      (cons 50 (/ pi 2))
				      (cons 1 pro) (cons 7 styl)))
		       )
		      )
		    )
		  )
		 ((< H1 H2); /
		  (entmake (list '(0 . "LINE") '(6 . "Continuous") (append '(10) t1) (append '(11) t22)))
		  (if (>(calculation_h_text_in_triang t2 t22 t1 (calculation_text_ratio_h_for_dlin (rtos S 2 2) ht styl))
			(calculation_h_text_in_triang t2 t1 t22 (calculation_text_ratio_h_for_dlin (rtos S 2 2) ht styl))
			)
		    (cond
		      ((> (*(calculation_h_text_in_triang t2 t22 t1 (calculation_text_ratio_h_for_dlin (rtos S 2 2) ht styl)) 0.8) (/ 3.5 (/ 1000 mg)))
		       (entmake (list '(0 . "TEXT") (cons 10 t1) '(72 . 2) '(73 . 0)
				      (cons 11 (mapcar '+ t2 (list (/(/ -3.5 (/ 1000 mg))3) (/(/ 3.5 (/ 1000 mg))3) )))
				      (cons 40 (/ 3.5 (/ 1000 mg)))
				      (cons 50 0)
				      (cons 1 (rtos S 2 2)) (cons 7 styl)))
		       )
		      ((< (*(calculation_h_text_in_triang t2 t22 t1 (calculation_text_ratio_h_for_dlin (rtos S 2 2) ht styl)) 0.8) (/ 1.6 (/ 1000 mg)))
		       (setq t3 (mapcar '+ t2 (list (/(distance t1 t2)2) (/ -1 (/ 1000 mg)) )))
		       (draw_mleader_vla model_spece (rtos S 2 2)(/ 2.5 (/ 1000 mg)) t3(mapcar '+ t3 (list (/ 2 (/ 1000 mg)) (/ -7 (/ 1000 mg)))))
		       )
		      (T
		       (entmake (list '(0 . "TEXT") (cons 10 t1) '(72 . 2) '(73 . 0)
				      (cons 11 (mapcar '+ t2 (list
							       (/(*(calculation_h_text_in_triang t2 t22 t1 (calculation_text_ratio_h_for_dlin (rtos S 2 2) ht styl)) -0.8)3)
							       (/(*(calculation_h_text_in_triang t2 t22 t1 (calculation_text_ratio_h_for_dlin (rtos S 2 2) ht styl)) 0.8)3)
							       )))
				      (cons 40 (*(calculation_h_text_in_triang t2 t22 t1 (calculation_text_ratio_h_for_dlin (rtos S 2 2) ht styl)) 0.8))
				      (cons 50 0)
				      (cons 1 (rtos S 2 2)) (cons 7 styl)))
		       )
		      )
		    (cond
		      ((> (*(calculation_h_text_in_triang t2 t1 t22 (calculation_text_ratio_h_for_dlin (rtos S 2 2) ht styl)) 0.8) (/ 3.5 (/ 1000 mg)))
		       (entmake (list '(0 . "TEXT")  '(72 . 0) '(73 . 0)
				      (cons 10 (mapcar '+ t2 (list (/(/ -3.5 (/ 1000 mg))3) (/(/ 3.5 (/ 1000 mg))3) )))
				      (cons 40 (/ 3.5 (/ 1000 mg)))
				      (cons 50 (/ pi 2))
				      (cons 1 (rtos S 2 2)) (cons 7 styl)))
		       )
		      ((< (*(calculation_h_text_in_triang t2 t1 t22 (calculation_text_ratio_h_for_dlin (rtos S 2 2) ht styl)) 0.8) (/ 1.6 (/ 1000 mg)))
		       (setq t3 (mapcar '- t2 (list (/(distance t1 t2)2) (/ -1 (/ 1000 mg)) )))
		       (draw_mleader_vla model_spece (rtos S 2 2)(/ 2.5 (/ 1000 mg)) t3(mapcar '+ t3 (list (/ 2 (/ 1000 mg)) (/ -7 (/ 1000 mg)))))
		       )
		      (T
		       (entmake (list '(0 . "TEXT")  '(72 . 0) '(73 . 0)
				      (cons 10 (mapcar '+ t2 (list
							       (/(*(calculation_h_text_in_triang t2 t1 t22 (calculation_text_ratio_h_for_dlin (rtos S 2 2) ht styl)) -0.8)3)
							       (/(*(calculation_h_text_in_triang t2 t1 t22 (calculation_text_ratio_h_for_dlin (rtos S 2 2) ht styl)) 0.8)3)
							       )))
				      (cons 40 (*(calculation_h_text_in_triang t2 t1 t22 (calculation_text_ratio_h_for_dlin (rtos S 2 2) ht styl)) 0.8))
				      (cons 50 (/ pi 2))
				      (cons 1 (rtos S 2 2)) (cons 7 styl)))
		       )
		      )
		    )
		  (if (>(calculation_h_text_in_triang t11 t1 t22 (calculation_text_ratio_h_for_dlin pro ht styl))
			(calculation_h_text_in_triang t11 t22 t1 (calculation_text_ratio_h_for_dlin pro ht styl))
			)
		    (cond
		      ((> (*(calculation_h_text_in_triang t11 t1 t22 (calculation_text_ratio_h_for_dlin pro ht styl)) 0.8) (/ 3.5 (/ 1000 mg)))
		       (entmake (list '(0 . "TEXT") (cons 10 t1) '(72 . 0) '(73 . 3)
				      (cons 11 (mapcar '+ t11 (list (/(/ 3.5 (/ 1000 mg))3) (/(/ -3.5 (/ 1000 mg))3) )))
				      (cons 40 (/ 3.5 (/ 1000 mg)))
				      (cons 50 0)
				      (cons 1 pro) (cons 7 styl)))
		       )
		      ((< (*(calculation_h_text_in_triang t11 t1 t22 (calculation_text_ratio_h_for_dlin pro ht styl)) 0.8) (/ 1.6 (/ 1000 mg)))
		       (setq t3 (mapcar '+ t11 (list (/(distance t1 t2)2) (/ -1 (/ 1000 mg)) )))
		       (draw_mleader_vla model_spece pro(/ 2.5 (/ 1000 mg)) t3(mapcar '+ t3 (list (/ 2 (/ 1000 mg)) (/ 7 (/ 1000 mg)))))
		       )
		      (T
		       (entmake (list '(0 . "TEXT") (cons 10 t1) '(72 . 0) '(73 . 3)
				      (cons 11 (mapcar '+ t11 (list
								(/(*(calculation_h_text_in_triang t11 t1 t22 (calculation_text_ratio_h_for_dlin pro ht styl)) 0.8)3)
								(/(*(calculation_h_text_in_triang t11 t1 t22 (calculation_text_ratio_h_for_dlin pro ht styl)) -0.8)3)
								)))
				      (cons 40 (*(calculation_h_text_in_triang t11 t1 t22 (calculation_text_ratio_h_for_dlin pro ht styl)) 0.8))
				      (cons 50 0)
				      (cons 1 pro) (cons 7 styl)))
		       )
		      )
		    (cond
		      ((> (*(calculation_h_text_in_triang t11 t22 t1 (calculation_text_ratio_h_for_dlin pro ht styl)) 0.8) (/ 3.5 (/ 1000 mg)))
		       (entmake (list '(0 . "TEXT") (cons 10 t1) '(72 . 2) '(73 . 3)
				      (cons 11 (mapcar '+ t11 (list (/(/ 3.5 (/ 1000 mg))3) (/(/ -3.5 (/ 1000 mg))3) )))
				      (cons 40 (/ 3.5 (/ 1000 mg)))
				      (cons 50 (/ pi 2))
				      (cons 1 pro) (cons 7 styl)))
		       )
		      ((< (*(calculation_h_text_in_triang t11 t22 t1 (calculation_text_ratio_h_for_dlin pro ht styl)) 0.8) (/ 1.6 (/ 1000 mg)))
		       (setq t3 (mapcar '+ t11 (list (/(distance t1 t2)2) (/ -1 (/ 1000 mg)) )))
		       (draw_mleader_vla model_spece pro(/ 2.5 (/ 1000 mg)) t3(mapcar '+ t3 (list (/ 2 (/ 1000 mg)) (/ 7 (/ 1000 mg)))))
		       )
		      (T
		       (entmake (list '(0 . "TEXT") (cons 10 t1) '(72 . 2) '(73 . 3)
				      (cons 11 (mapcar '+ t11 (list
								(/(*(calculation_h_text_in_triang t11 t22 t1 (calculation_text_ratio_h_for_dlin pro ht styl)) 0.8)3)
								(/(*(calculation_h_text_in_triang t11 t22 t1 (calculation_text_ratio_h_for_dlin pro ht styl)) -0.8)3)
								)))
				      (cons 40 (*(calculation_h_text_in_triang t11 t22 t1 (calculation_text_ratio_h_for_dlin pro ht styl)) 0.8))
				      (cons 50 (/ pi 2))
				      (cons 1 pro) (cons 7 styl)))
		       )
		      )
		    )
		  )
		 )
	       )
	     )
	   (if (/= (length spisokv) 0)
	     (setq t0 (mapcar '+ t0 (list (distance (list (nth 0 p1) (nth 1 p1)) (list (nth 0 p2) (nth 1 p2))) 0 0)))
	     )
	   )
	 (setq spisokv (extract_coord_lwpolyline (entget 2Dpline)))
	 (setq n (length spisokv))
	 (repeat n
	   (setq p (car spisokv))
	   (setq spisokv (cdr spisokv))
	   (entmake (list '(0 . "LINE") '(6 . "Continuous") (cons 10 (list (nth 0 p)(nth 1 t2_draw_uklon))) (cons 11 (list (nth 0 p)(nth 1 t1_draw_uklon)))))
	   )
	 )
