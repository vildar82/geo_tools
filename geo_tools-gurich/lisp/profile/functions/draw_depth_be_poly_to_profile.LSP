(defun C:draw_depth_be_poly_to_profile (/ plinef plined spisokv_f spisokv_d n_f n_d pf pd glud ht styl); вычисляет глубину заложения между двумя полилиниями
(geo_tools-help "draw_depth_be_poly_to_profile")
  (setq plinef (get_2dpoly "\nВыбери верхнюю ПОЛИЛИНИЮ: "))
  (setq plined (get_2dpoly "\nВыбери нижнюю ПОЛИЛИНИЮ: "))
  (setq mv (file_dat_r_g_w "r" "mv" nil))
  (initget)(setq t1(getpoint "\nУкажи нижнюю линию строки: "))
  (initget)(setq t2(getpoint "\nУкажи верхнюю линию строки: "))
  (setq spisokv_f (extract_coord_lwpolyline plinef))
  (setq spisokv_d (extract_coord_lwpolyline plined))
  (setq n_f (length spisokv_f))
  (setq n_d (length spisokv_d))
  (if
    (= n_f n_d)
    (progn
      (repeat n_f
	(setq pf (car spisokv_f))
	(setq spisokv_f (cdr spisokv_f))
	(setq pd (car spisokv_d))
	(setq spisokv_d (cdr spisokv_d))
	(setq glud (rtos (* (- (nth 1 pf) (nth 1 pd))(/ (* mv (getvar "CANNOSCALEVALUE")) 1000)) 2 2))
	(setq ht (/ 3.5 (getvar "CANNOSCALEVALUE")))
	(setq styl (getvar "TEXTSTYLE"))
	(entmake (list '(0 . "TEXT")
		       (cons 10 (list (-(nth 0 pf) (/ ht 4)) (+(nth 1 t1)(-(/(- (nth 1 t2)(nth 1 t1))2)(/(calculation_str_long_be_h_stile glud ht styl)2)))))
		       (cons 40 ht)
		       (cons 50 (/ pi 2))
		       (cons 1 glud)
		       (cons 7 styl)))
	))
    (princ "Количество узлов не совпадает!")
    )
  (princ)
  )
