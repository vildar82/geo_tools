(defun C:draw_elevation_to_profile (/ t1 h t2)
  ; Ставит маркер на указанном превышении от указаной точки
  (geo_tools-help "draw_elevation_to_profile")
  (setq mv (file_dat_r_g_w "r" "mv" nil))
  (setq mg (file_dat_r_g_w "r" "mg" nil))
  (setq usl_z (file_dat_r_g_w "r" "usl_z" nil))
  (setq t1(get_p_usl_z_m_mg "\nУкажи точку "))
  (while
    (not (and (= mv nil) (= t1 nil)))
    (initget 1)(setq h (getreal "\nВведи превышение: "))
    (setq t2 (mapcar '+ t1 (list 0 (/ h(/ (* mv (/ 1000 mg)) 1000)))))
    (entmake (list '(0 . "LINE") '(6 . "Continuous") (append '(10) t1) (append '(11) t2)))
    (entmake (list '(0 . "LWPOLYLINE") '(100 . "AcDbEntity") '(6 . "Continuous") '(100 . "AcDbPolyline")
		   '(90 . 3) '(70 . 1) (cons 43 0)
		   (cons 10 (mapcar '+ t2 (list -1.25 -2.165)))
		   (cons 10 t2)
		   (cons 10 (mapcar '+ t2 (list 1.25 -2.165)))
		   )
	     )
    (setq t1(get_p_usl_z_m_mg"\nУкажи точку "))
    )
  )
