(defun C:draw_to_profile_ellipse_tr_ (/ t1 d r z); Рисует элипс пересекаемой трубы указываемым диаметром
(geo_tools-help "draw_to_profile_ellipse_tr_")
  (setq mv (file_dat_r_g_w "r" "mv" nil))
  (setq mg (file_dat_r_g_w "r" "mg" nil))
  (setq usl_z (file_dat_r_g_w "r" "usl_z" nil))
  (setq t1(get_p_usl_z_m_mg "\nУкажи точку вставки(ось) "))
  (while
    (not (and (= mv nil) (= t1 nil)))
    (initget 1)(setq d (getreal "\nВведи диаметр в мм : "))
    (setq d (/ d 1000))
    (setq z (/ mv mg))
    (setq r (/ (/ d 2)z))
    (entmake (list '(0 . "ELLIPSE")
		   '(100 . "AcDbEntity")
		   '(6 . "Continuous")
		   '(100 . "AcDbEllipse")
		   (cons 10 t1)
		   (cons 11 (cons 0.0 (cons (- r (* r 2)) '(0.0))))
		   '(210 0.0 0.0 1.0)
		   (cons 40 z)
		   '(41 . 0.0)
		   (cons 42 (* pi 4))
		   )
	     )
    (setq t1(get_p_usl_z_m_mg "\nУкажи точку вставки(ось) "))
    )
  )
