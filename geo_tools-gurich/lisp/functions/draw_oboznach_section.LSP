(defun C:draw_oboznach_section ( / mg t1 t2 t3 ugol str)
  (geo_tools-help "draw_oboznach_section")
  (setq mg (/ 1.0 (getvar "CANNOSCALEVALUE")))
  (initget)(setq t1(getpoint "\nУкажи первую точку сечения:"))
  (initget)(setq t2(getpoint t1 "\nУкажи вторую точку сечения:"))
  (entmake (list '(0 . "LINE") '(370 . 30) (cons 10 (polar t1 (angle t1 t2) (* 2 mg))) (cons 11 (polar t1 (angle t2 t1) (* 2 mg)))))
  (entmake (list '(0 . "LINE") '(370 . 30) (cons 10 (polar t2 (angle t1 t2) (* 2 mg))) (cons 11 (polar t2 (angle t2 t1) (* 2 mg)))))
  (initget)(setq t3(getpoint t2 "\nУкажи направление:"))
  (if (minusp(*(distance t2 t3) (cos (- pi (- (- (angle t2 t1)(angle t2 t3)) (/ pi 2))))))
    (setq ugol (-(angle t2 t1) (/ pi 2)))
    (setq ugol (+(angle t2 t1) (/ pi 2)))
    )
  (entmake (list '(0 . "LWPOLYLINE") '(100 . "AcDbEntity") '(6 . "Continuous") '(100 . "AcDbPolyline")
		 '(90 . 3)
		 (cons 10 t1) '(40 . 0.0) (cons 41 (* 1 mg)) '(42 . 0.0)
		 (cons 10 (polar t1 ugol (* 2 mg))) '(40 . 0.0) '(41 . 0.0) '(42 . 0.0)
		 (cons 10 (polar t1 ugol (* 7 mg))) '(40 . 0.0) '(41 . 0.0) '(42 . 0.0)
		 )
	   )
  (entmake (list '(0 . "LWPOLYLINE") '(100 . "AcDbEntity") '(6 . "Continuous") '(100 . "AcDbPolyline")
		 '(90 . 3)
		 (cons 10 t2) '(40 . 0.0) (cons 41 (* 1 mg)) '(42 . 0.0)
		 (cons 10 (polar t2 ugol (* 2 mg))) '(40 . 0.0) '(41 . 0.0) '(42 . 0.0)
		 (cons 10 (polar t2 ugol (* 7 mg))) '(40 . 0.0) '(41 . 0.0) '(42 . 0.0)
		 )
	   )
  (initget 1)(setq str(getstring "\nВведи номер сечения: " ))
  (entmake (list '(0 . "TEXT")
		 (cons 10 t1)
		 '(72 . 1) '(73 . 1)
		 (cons 11 (polar t1 ugol (* 5.8 mg)))
		 (cons 40 (* 2.5 mg))
		 (cons 1 str)
		 (cons 50 (analysis_angle_be_long_distance ugol))
		 (cons 7 (getvar "TEXTSTYLE"))))
  
  (entmake (list '(0 . "TEXT")
		 (cons 10 t2)
		 '(72 . 1) '(73 . 1)
		 (cons 11 (polar t2 ugol (* 5.8 mg)))
		 (cons 40 (* 2.5 mg))
		 (cons 1 str)
		 (cons 50 (analysis_angle_be_long_distance ugol))
		 (cons 7 (getvar "TEXTSTYLE"))))
  (princ)
  )
