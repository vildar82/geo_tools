(defun C:draw_text_be_any_style ( / t1 a h b style osn)
  (geo_tools-help "draw_text_be_any_style")
;;;  (format_check_text_style)
  (initget)(setq style (getstring T "\nКакой стиль текста будем использовать?: "))
  (cond
    ((eq style "OTI")
     (setq h (/ (/ 3 (format_scale_kof)) 1.5)))
    ((eq style "OTI")
     (setq h (/ (/ 2 (format_scale_kof)) 1.05994)))
    ((eq style "OTI")
     (setq h (/ (/ 2 (format_scale_kof)) 1)))
    ((eq style "OTI")
     (setq h (/ (/ 2.5 (format_scale_kof)) 1)))
    ((eq style nil)
     (setq h (/ (/ 2.5 (format_scale_kof)) 1))
     (setq style (getvar "TEXTSTYLE")))
    (T
     (setq h (/ (/ 2 (format_scale_kof)) 1)))
    )
  (initget)(setq t1(getpoint "\nУкажи точку вставки текста:")); указываю точку
  (initget)(setq a (getangle t1 "\nВведи угол поворота или укажи направление:")); указываю угол
  (if (eq a nil)
    (setq a (* pi 1.5))
    )
  (setq b (- (* pi 2) a))
  (setq b (strcat (itoa(fix(/ b (/ pi 180))))
		  "d"
		  (itoa(fix(*(-(/ b (/ pi 180))(fix(/ b (/ pi 180))))60)))
		  "'"
		  (itoa(fix(*(-(*(-(/ b (/ pi 180))(fix(/ b (/ pi 180))))60)(fix(*(-(/ b (/ pi 180))(fix(/ b (/ pi 180))))60)))60)))
		  "\"")
	)
  (princ "\nВведи текст: ")
  (setq osn (getvar "OSMODE"))
  (setvar "OSMODE" 0)
  (setvar "CMDECHO" 0)
  (command "_dtext" "_s" style t1 h b)
  (setvar "OSMODE" osn)
  (setvar "CMDECHO" 1)
  (princ)
  )
