(defun C:edit_resize_line_and_2point_poly (/ line line_odj p t1 t2 t1n t2n dist new_dist spisokv); изменение длинны линии
  (geo_tools-help "edit_resize_line_and_2point_poly")
  (redraw)
  (setq line_odj (entsel "\nВыбери линию: "))
  (setq p (cadr line_odj))
  (setq line (car line_odj))
  (if (not(eq line_odj nil))
    (if (or (eq (cdr (assoc 0 (entget line))) "LINE") (and (eq (cdr (assoc 0 (entget line))) "LWPOLYLINE")(eq (cdr (assoc 90 (entget line))) 2)))
      (progn
	(if (eq (cdr (assoc 0 (entget line))) "LINE")
	  (progn
	    (setq t1 (cdr (assoc 10 (entget line))))
	    (setq t2 (cdr (assoc 11 (entget line))))
	    )
	  (progn
	    (setq spisokv (extract_coord_lwpolyline (entget line)))
	    (setq t1 (car spisokv))
	    (setq t2 (cadr spisokv))
	    )
	  )
	(setq dist (distance t1 t2))
	(cond
	  ((< (distance p t1)  (/(distance t2 t1)3))
	   (draw_temp_X t1 1)
	   )
	  ((< (distance p t2)  (/(distance t2 t1)3))
	   (draw_temp_X t2 1)
	   )
	  ((and(> (distance p t2)  (/(distance t2 t1)3))(> (distance p t1)  (/(distance t2 t1)3)))
	   (draw_temp_X t1 1)
	   (draw_temp_X t2 1)
	   )
	  )
	(initget 6)(setq new_dist(getreal(strcat "\nУкажи новую длинну линии <" (rtos dist 2 3) ">:")))
	(if (eq new_dist nil)(setq new_dist dist))
	(redraw)
	(if (not(eq dist nil))
	  (progn
	    (cond
	      ((< (distance p t1)  (/(distance t2 t1)3))
	       (setq t1n (polar t1  (angle t1 t2) (- dist new_dist)))
	       (setq t2n t2)
	       )
	      ((< (distance p t2)  (/(distance t2 t1)3))
	       (setq t1n t1)
	       (setq t2n (polar t2  (angle t2 t1) (- dist new_dist)))
	       )
	      ((and(> (distance p t2)  (/(distance t2 t1)3))(> (distance p t1)  (/(distance t2 t1)3)))
	       (setq t1n (polar t1  (angle t1 t2) (/ (- dist new_dist) 2)))
	       (setq t2n (polar t2  (angle t2 t1) (/ (- dist new_dist) 2)))
	       )
	      )
	    (if (eq (cdr (assoc 0 (entget line))) "LINE")
	      (entmod (list (cons -1 line) (cons 10 t1n) (cons 11 t2n) ))
	      (progn
		(entmod(subst (cons 10 t1n)(cons 10 t1) (entget line)))
		(entmod(subst (cons 10 t2n)(cons 10 t2) (entget line)))
		)
	      )
	    )
	  )
	)
      (alert "Выбран не допустимый объект!")
      )
    )
  (princ)
  )
