(defun C:edit_text_style ( / style)
  (geo_tools-help "edit_text_style")
  (initget)(setq style (getstring T "\nКакой стиль текста будем использовать?: "))
  (cond
    ((eq style "OTI")
     (edit_convert_text_style_to_rub))
    ((eq style "OTI")
     (edit_convert_text_style_to_bsam))
    ((eq style "OTI")
     (edit_convert_text_style_to_drevn))
    ((eq style "OTI")
     (edit_convert_text_style_to_gost))
    )
  (princ)
  )
