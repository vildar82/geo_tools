(defun C:save_select_obj ( / ssnab x)
  (load_global_variable)
  (cond
    ((setq ssnab (ssget "_I"))
     (princ)
     )
    ((setq ssnab (ssget))
     (princ)
     )
    (T
     (exit)
     )
    )
  (setq *save-select-obj* nil)
  (foreach x (convert_ss_to_list ssnab)
    (setq *save-select-obj* (append *save-select-obj* (list (vlax-ename->vla-object x))))
    )
  (princ (strcat "\nЗапомнил "(itoa(length *save-select-obj*)) " объектов."))
  (princ)
  )
