(defun C:format_check_line_typ (/ linetyp_name)
(geo_tools-help "format_check_line_typ")
  (load_global_variable)
  (initget 1 )(setq linetyp_name (getstring T "\nВведи имя типа линии: "))
  (if (not (tblobjname "ltype" linetyp_name))
    (vla-load (vla-get-Linetypes active_document) linetyp_name "Линии.lin")
    )
  (vla-put-ActiveLinetype active_document (vla-item (vla-get-linetypes active_document) linetyp_name))
  )
