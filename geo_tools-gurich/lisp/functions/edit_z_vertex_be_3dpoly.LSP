(defun C:edit_z_vertex_be_3dpoly (/ pline vla_pline n vertix z point obj t_pik par nabor p spisokv); позволяет изменить отметку у выбранной вершины 3D полилини
  (geo_tools-help "edit_z_vertex_be_3dpoly")
  (setq obj (entsel "\nВыберите 3D полилинию: "))
  (if (and (/= obj nil)(eq (cdr (assoc 0 (entget (car obj)))) "POLYLINE"))
    (progn
      (while
	(/= obj nil)
	(setq nabor nil)
	(setq pline (car obj))
	(setq vla_pline(vlax-ename->vla-object pline))
	(setq t_pik (cadr obj))
	(setq par (atof(rtos(vlax-curve-getParamAtPoint vla_pline (vlax-curve-getClosestPointTo vla_pline t_pik))2 0)))
	(setq point (vlax-curve-getPointAtParam vla_pline par))
	(draw_temp_X point 1)
	(setq spisokv (extract_coord_polyline pline))
	(setq n (vl-position point spisokv))
	(setq vertix (entnext pline))
	(repeat n
	  (setq vertix (entnext vertix))
	  )
	(setq nabor (ssadd pline))
	(sssetfirst nabor nabor)
	(princ (strcat "\nТекущая отметка вершины = "  (rtos (nth 2 (cdr(assoc 10 (entget vertix)))) 2 2)))
	(setq z(get_elivation))
	(if (eq z nil) (setq z  (nth 2 (cdr(assoc 10 (entget vertix))))))
	(setq p (list (nth 0 (cdr (assoc 10 (entget vertix)))) (nth 1 (cdr(assoc 10 (entget vertix)))) z))
	(entmod (subst (cons 10 p)(assoc 10 (entget vertix)) (entget vertix)))
	(entupd pline)
	(sssetfirst)
	(redraw)
	(setq t_pik nil)
	(setq obj (entsel "\nВыберите 3D полилинию: "))
	)
      )
    (alert "Ничего не выбрано или выбран не допустимый объект!"))
  (princ)
  )
