(defun C:draw_text_long_and_diam_be_2_points (/ t1 t2 mtext_obj str temp)
  (geo_tools-help "draw_text_long_and_diam_be_2_points")
  (if (eq str1 nil)
    (setq str "\nВведи верхнюю строку: ")
    (setq str (strcat "\nВведи верхнюю строку<" str1 "> : ")))
  (initget)(setq temp (getstring T str))
  (if (/= temp "")
    (setq str1 temp))
  (while (/= str1 "")
    (initget)(setq t1(getpoint "\nУкажи первую точку: "))
    (if (eq t1 nil)(exit))
    (initget)(setq t2(getpoint t1 "\nУкажи вторую точку: "))
    (if (eq t2 nil)(exit))
    (setq mtext_obj (vla-AddMText model_spece (vlax-3D-point (polar t1 (angle t1 t2) (/ (distance t1 t2) 2))) 12 (strcat"\\pxqc;"str1"\\PL=" (rtos(distance t1 t2)2 2) "м")))
    (vla-put-AttachmentPoint mtext_obj 5)
    (vla-put-InsertionPoint mtext_obj (vlax-3D-point (polar t1 (angle t1 t2) (/ (distance t1 t2) 2))))
    (vla-put-Height mtext_obj (/ 2.0 (getvar "CANNOSCALEVALUE")))
    (vla-put-Rotation mtext_obj (analysis_angle_be_long_distance (angle t1 t2)))
    )
  (progn)
  )
