(defun C:edit_add_special_symbol_to_text ( / symbol_stroka_ NK str ttt)
(geo_tools-help "edit_add_special_symbol_to_text")
(initget)(setq text (car (entsel "\nВыбери текст: ")))
  (if
    (or (eq (cdr (assoc 0 (entget text))) "TEXT") (eq (cdr (assoc 0 (entget text))) "MTEXT"))
    (progn
      (setq symbol "%%d")
    (setq dcl_id (geo-tools-load-dialog "d_add_symbol"))
  (new_dialog "d_add_symbol" dcl_id)
  (action_tile "radio1_0" "(setq symbol \"%%d\")")
  (action_tile "radio1_1" "(setq symbol \"%%p\")")
  (action_tile "radio1_2" "(setq symbol \"%%c\")")
  (action_tile "radio1_3" "(setq symbol \"\U+03A3\")")
  (action_tile "radio1_4" "(setq symbol \"\U+00B2\")")
  (action_tile "radio1_5" "(setq symbol \"\U+00B3\")")
  (action_tile "radio1_6" "(setq symbol \"\U+2082\")")
  (action_tile "radio1_7" "(setq symbol \"%%u\")")
  (action_tile "radio1_8" "(setq symbol \"%%o\")")
  (action_tile "radio2_0" "(setq NK \"Начале\")")
  (action_tile "radio2_1" "(setq NK \"Конце\")")
  (if (eq (start_dialog) 0) (progn (unload_dialog dcl_id)(exit))(unload_dialog dcl_id))
  (setq ttt (entget text))
  (setq str (cdr (assoc 1 ttt)))
  (if
    (= NK "Начале")
    (setq str (strcat symbol str))
    (setq str (strcat str symbol))
    )
  (entmod (subst (cons 1 str)(assoc 1 ttt) ttt))
  (entupd text)
    )
    )
  (princ)
  )
