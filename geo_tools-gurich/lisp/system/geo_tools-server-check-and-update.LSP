(defun geo_tools-server-check-and-update ()
  (if (get-server-check-update-flag)
    (if(>(cadr (get-server-version-geo_tools)) 0)
      (if (<(cadr (get-curent-version-geo_tools))(cadr (get-server-version-geo_tools)))
	(progn
	  (princ (strcat "\nНа сервере есть более новая версия "(car(get-server-version-geo_tools))))
	  (if (get-server-auto-update-flag)
	    (progn
	      (princ  "\nАвтоматическое обновление включено. Начинаю замену файлов...")
	      (geo_tools-update-from-server)
	      )
	    (princ  "\nАвтоматическое обновление выключено. Рекомендуется обновить Geo_tools.")
	    )
	  )
	)
      (princ  "\nНет доступа к обновлениям Geo_tools или неверный путь.")
      )
    )
  )
