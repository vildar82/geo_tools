(defun geo-tools-compile-lsp ( / lsp_list result-list n output-lsp-file)
  (setq output-lsp-file (strcat *geo_tools_root_dir* "\\lisp\\all-integration-fun.lsp"))
  (if(file-p output-lsp-file)(vl-file-delete output-lsp-file))
  (setq lsp_list (file_find_be_extension (strcat *geo_tools_root_dir* "\\lisp") "lsp"))
  (setq n 0)
  (foreach x lsp_list
    (if (or(wcmatch x "*=dont-comile=*")(wcmatch x "*=without-fail-loading=*"))
      (setq n (1+ n))
      (setq result-list (append result-list(file_read_to_list x)))
      )
    )
  (file_write_list_to_file output-lsp-file result-list)
  (vlisp-compile 'lsa output-lsp-file)
  (if(file-p output-lsp-file)(vl-file-delete output-lsp-file))
  (file_write_list_to_file (strcat *geo_tools_root_dir* "\\lisp\\all-compile-fun.prv")
    (list
      "(PRV-DEF (:target . \"all-compile-fun.VLX\")
	   (:active-x . T)
	   (:separate-namespace)
	   (:protected . T)
	   (:load-file-list (:lsp \"all-integration-fun.fas\"))
	   (:require-file-list (:DCL \"Диалоговые окна.dcl\"))
	   (:ob-directory)
	   (:tmp-directory)
	   (:optimization . lsa)
	   )"
      )
    )
  (princ)
  )
