(defun edit_text_clean_for_number (text_str / text_obj text_list new_text_list n simvol);clean_text_for_number
  (setq text_list (vl-string->list text_str))
  (setq n 0)
  (repeat (length text_list)
    (setq simvol (nth n text_list))
    (cond
      ((wcmatch (chr simvol) "#")
       (setq new_text_list (append new_text_list(list simvol))))
      ((wcmatch (chr simvol) "@")
       )
      ((wcmatch (chr simvol) "`.")
       (if (/= n 0)
	 (if (and (/= (1+ n) (length text_list))(wcmatch (chr (nth (1- n) text_list)) "#")(wcmatch (chr (nth (1+ n) text_list)) "#"))
	   (setq new_text_list (append new_text_list(list simvol)))
	   )
	 )
       )
      ((wcmatch (chr simvol) "`,")
       (if (/= n 0)
	 (if (and (/= (1+ n) (length text_list))(wcmatch (chr (nth (1- n) text_list)) "#")(wcmatch (chr (nth (1+ n) text_list)) "#"))
	   (setq new_text_list (append new_text_list(list (ascii "."))))
	   )
	 )
       )
      )
    (setq n (1+ n))
    )
  (vl-list->string new_text_list)
  )
