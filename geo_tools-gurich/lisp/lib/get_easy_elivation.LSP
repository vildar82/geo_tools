(defun get_easy_elivation(/ flag obj z temp)
  (load_global_variable)
  (setq flag T)
  (while flag
    (initget "Ввести выХод")
    (setq temp(entsel "\nВыбери точку или текст с отметкой[Ввести/выХод]<Ввести>: "))
    (if (eq(type temp)'list)
      (setq obj (car temp))
      (setq obj temp))
    (cond
      ((eq obj "выХод")
       (setq z nil)
       (setq flag nil)
       )
      ((or(eq obj nil)(eq obj "Ввести"))
       (setq z (getreal"\nВведи отметку<0.00>: "))
       (if (eq z nil) (setq z 0.0))
       (setq flag nil)
       )
      ((eq (cdr(assoc 0 (entget obj))) "TEXT")
       (setq z(atof(edit_text_clean_for_number(cdr(assoc 1(entget obj))))))
       (setq flag nil)
       )
      ((eq (cdr(assoc 0 (entget obj))) "AECC_COGO_POINT")
       (setq z(vlax-get-property  (vlax-ename->vla-object obj) "ELEVATION"))
       (setq flag nil)
       )
      (T
       (alert "Ошибка! Выбран не объект не допустимого типа. Допускаются однострочный текст и точки COGO. Попробуй снова.")
       )
      )
    )
  z
  )
