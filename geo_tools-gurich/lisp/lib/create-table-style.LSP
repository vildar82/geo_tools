(defun create-table-style (/ item)
  ; создает стиль таблиц каталога координат
  (if(vl-catch-all-error-p
       (vl-catch-all-apply 'vla-item
	 (list (vla-item (vla-get-dictionaries
			   (vla-get-activedocument (vlax-get-acad-object))
			   )"acad_tablestyle") "Координаты"))); проверяем наличие отсутствия стиля таблиц
    (progn
;;;      (create-text-style "OTI" "ESKDU.shx")
      (setq
	item (vla-addobject
	       (vla-item (vla-get-dictionaries
			   (vla-get-activedocument (vlax-get-acad-object))
			   );_ end of vla-get-dictionaries
			 "acad_tablestyle"
			 );_ end of vla-item
	       "Координаты"
	       "AcDbTableStyle"
	       );_ end of vla-AddObject
	);_ end of setq
      (vla-put-name item "Координаты"); имя стиля
      (vla-put-description item "Таблица каталога координат"); описание стиля
      (vla-put-flowdirection item 0); направление (?)
      (vla-put-horzcellmargin item 0.5); гориз.отступ текста от границы ячейки
      (vla-put-vertcellmargin item 0.5); верт.отступ текста от границы ячейки
      (vla-settextheight
	item
	acdatarow
	2.0
	); высота текста по умолчанию для datacells
      (vla-settextheight
	item
	acheaderrow
	2.0
	); высота текста для шапки таблицы
      (vla-settextheight
	item
	actitlerow
	2.0
	); высота текста для заголовка таблицы
      (vla-settextstyle
	item
	(+ acdatarow acheaderrow actitlerow)
	(getvar "TEXTSTYLE")
	); стиль текста по умолчанию для всех ячеек
      (vla-setgridvisibility
	item
	(+ achorztop acvertleft acvertright)
	actitlerow
	:vlax-false
	);_ end of vla-SetGridVisibility отключаем рамку вокруг названия
      (vla-setgridvisibility
	item
	(+ achorzinside acvertinside achorztop achorzbottom acvertleft acvertright)
	(+ acdatarow acheaderrow)
	:vlax-true
	);_ end of vla-SetGridVisibility включаем рамки вокруг всего остального (не знаю зачем:))
      T
      )
    nil
    )
  );_ end of defun
