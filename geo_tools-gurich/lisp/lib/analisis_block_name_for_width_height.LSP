(defun analisis_block_name_for_width_height (block_name / block_name_list width height)
  ; извлекает из текстовой строки имени формата ширину и высоту
  (setq block_name_list (vl-string->list block_name))
  (setq block_name_list (reverse block_name_list))
  (while (not(eq (car block_name_list) (ascii "x")))
    (setq width (append width (list(car block_name_list))))
    (setq block_name_list (cdr block_name_list))
    )
  (setq block_name_list (cdr block_name_list))
  (while (not(eq (car block_name_list) (ascii " ")))
    (setq height (append height (list(car block_name_list))))
    (setq block_name_list (cdr block_name_list))
    )
  (setq width (atof(vl-list->string(reverse width))))
  (setq height (atof(vl-list->string(reverse height))))
  (if (eq (substr block_name 1 3) "ISO")
    (progn
      (setq temp width)
      (setq width height)
      (setq height temp)))
  (list width height)
  )
