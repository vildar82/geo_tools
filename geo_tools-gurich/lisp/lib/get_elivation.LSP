(defun get_elivation (/ z z_summa list_z x z_srednee temp list_num_points num_point list_add_z nabor n ss)
  ; функция запроса отметок вычисления из них среднего и внесения поправки
  (load_global_variable)
  (setq z 0.0)
  (if (eq popravka nil)(setq popravka 0.0))
  (while (not (eq z nil))
    (setq z_summa 0.0)
    (foreach x list_z (setq z_summa (+ z_summa x)))
    (if (/=(length list_z)0)
      (setq z_srednee (/ z_summa (length list_z)))
      (setq z_srednee 0.0)
      )
    (if (/=(length list_z)0)
      (progn
	(initget "ПОПравка ОБЪекты ОТМена")
	(setq z (getreal (strcat"\nИзмерений: "(itoa (length list_z))
				" Среднее: " (rtos z_srednee 2 2)
				" Поправка: " (rtos popravka 2 2)
				" Результат: "(rtos (+ z_srednee popravka) 2 2)
				" Введи отметку или [ПОПравка/ОБЪекты/ОТМена]<ПРОДОЛЖИТЬ>: ")))
	)
      (progn
	(initget "ПОПравка ОБЪекты")
	(setq z (getreal (strcat"\nИзмерений: "(itoa (length list_z))
				" Среднее: " (rtos z_srednee 2 2)
				" Поправка: " (rtos popravka 2 2)
				" Результат: "(rtos (+ z_srednee popravka) 2 2)
				" Введи отметку или [ПОПравка/ОБЪекты]<ПРОДОЛЖИТЬ>: ")))
	)
      )
    (cond
      ((eq z "ПОПравка")
       (initget)
       (setq temp(getreal (strcat "\nВведи поправку к отметке<"(rtos popravka 2 3)">: ")))
       (if
	 (/= temp nil)
	 (setq popravka temp)
	 )
       )
      ((eq z "ОБЪекты")
       (setq ss (ssget '((0 . "TEXT,AECC_COGO_POINT"))))
       (if ss
	 (foreach x (convert_ss_to_list ss)
	   (if (eq (cdr(assoc 0 (entget x))) "TEXT")
	     (setq list_add_z (append list_add_z (list(atof(edit_text_clean_for_number(cdr(assoc 1(entget x))))))))
	     (setq list_add_z(append list_add_z (list(vlax-get-property  (vlax-ename->vla-object x) "ELEVATION"))))
	     )
	   )
	 )
       )
      ((eq z "ОТМена")
       (setq list_z (reverse(cdr(reverse list_z))))
       )
      ((eq 'REAL (type z))
       (setq list_add_z (append (list z)))
       )
      )
    (if list_add_z
    (setq list_z(append list_z list_add_z))
      )
    (setq list_add_z nil)
    )
  (+ z_srednee popravka)
  )
