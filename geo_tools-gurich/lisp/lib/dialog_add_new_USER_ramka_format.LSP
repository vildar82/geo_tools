(defun dialog_add_new_USER_ramka_format ( / dcl_id deskr H_ramka D_ramka new_format)
  (setq deskr "")
  (setq H_ramka "0")
  (setq D_ramka "0")
  (setq dcl_id (geo-tools-load-dialog "d_new_USER_format"))
  (new_dialog "d_new_USER_format" dcl_id)
  (action_tile "deskr" "(setq deskr (get_tile \"deskr\"))")
  (action_tile "H_ramka" "(setq H_ramka (get_tile \"H_ramka\"))")
  (action_tile "D_ramka" "(setq D_ramka (get_tile \"D_ramka\"))")
  (if (/= (start_dialog) 0)
    (progn
      (setq new_format (strcat "USER " deskr " (" H_ramka "x" D_ramka")"))
      (file_write_list_to_file (strcat *geo_tools_user_dat_dir*"\\data\\USER.dat") (append(reading_file_dat_format_manager "USER.dat")(list new_format)))
      )
    )
  )
