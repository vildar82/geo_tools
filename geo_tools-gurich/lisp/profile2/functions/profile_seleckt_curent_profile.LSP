(defun C:profile_seleckt_curent_profile (/ curent-profile list-name-block-profile new-curent-profile)
  ; позволяет выбрать (указателем или из падающего списка) текущий профиль
  (geo_tools-help "profile_seleckt_curent_profile")
  (profile-seleckt-curent-mode)
  (princ)
  )
