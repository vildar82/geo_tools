(defun analysis_point_11 (long text t1 t2 t4 t5 /)
  (cond
  ((= (angle t1 t2) long)
   (if (> d 0)
     (cond
       ((equal t10 t1 1)
	(polar (polar t1 (angle t1 t5) (+ (/ 0.5 (getvar "CANNOSCALEVALUE")) (calculation_text_long_be_dxf_code text))) (angle t1 t2) (/ 0.5 (getvar "CANNOSCALEVALUE")))
	)
       ((equal t10 t2 1)
	(polar (polar t2 (angle t1 t5) (+ (/ 0.5 (getvar "CANNOSCALEVALUE")) (calculation_text_long_be_dxf_code text))) (angle t2 t1) (+ (/ 0.5 (getvar "CANNOSCALEVALUE")) (calculation_text_height_be_dxf_code text)))
	)
       ((equal t10 t4 1)
	(polar (polar t4 (angle t5 t1) (/ 0.5 (getvar "CANNOSCALEVALUE"))) (angle t2 t1) (+ (/ 0.5 (getvar "CANNOSCALEVALUE")) (calculation_text_height_be_dxf_code text)))
	)
       ((equal t10 t5 1)
	(polar (polar t5 (angle t5 t1) (/ 0.5 (getvar "CANNOSCALEVALUE"))) (angle t1 t2) (/ 0.5 (getvar "CANNOSCALEVALUE")))
	)
       ( T "Не попадено в точку 1-2 +")
       ); cond
     (cond
       ((equal t10 t1 1)
	(polar (polar t1 (angle t1 t5) (/ 0.5 (getvar "CANNOSCALEVALUE"))) (angle t1 t2) (/ 0.5 (getvar "CANNOSCALEVALUE")))
	)
       ((equal t10 t2 1)
	(polar (polar t2 (angle t1 t5) (/ 0.5 (getvar "CANNOSCALEVALUE"))) (angle t2 t1) (+ (/ 0.5 (getvar "CANNOSCALEVALUE")) (calculation_text_height_be_dxf_code text)))
	)
       ((equal t10 t4 1)
	(polar (polar t4 (angle t5 t1) (+ (/ 0.5 (getvar "CANNOSCALEVALUE")) (calculation_text_long_be_dxf_code text))) (angle t2 t1) (+ (/ 0.5 (getvar "CANNOSCALEVALUE")) (calculation_text_height_be_dxf_code text)))
	)
       ((equal t10 t5 1)
	(polar (polar t5 (angle t5 t1) (+ (/ 0.5 (getvar "CANNOSCALEVALUE")) (calculation_text_long_be_dxf_code text))) (angle t1 t2) (/ 0.5 (getvar "CANNOSCALEVALUE")))
	)
       ( T "Не попадено в точку 1-2 -")
       ); cond
     ); if
   );
  ((= (angle t2 t1) long)
   (if (> d 0)
     (cond
       ((equal t10 t1 1)
	(polar (polar t1 (angle t1 t5) (/ 0.5 (getvar "CANNOSCALEVALUE"))) (angle t1 t2) (+ (/ 0.5 (getvar "CANNOSCALEVALUE")) (calculation_text_height_be_dxf_code text)))
	)
       ((equal t10 t2 1)
	(polar (polar t2 (angle t1 t5) (/ 0.5 (getvar "CANNOSCALEVALUE"))) (angle t2 t1) (/ 0.5 (getvar "CANNOSCALEVALUE")))
	)
       ((equal t10 t4 1)
	(polar (polar t4 (angle t5 t1) (+ (/ 0.5 (getvar "CANNOSCALEVALUE")) (calculation_text_long_be_dxf_code text))) (angle t2 t1) (/ 0.5 (getvar "CANNOSCALEVALUE")))
	)
       ((equal t10 t5 1)
	(polar (polar t5 (angle t1 t5) (+ (/ 0.5 (getvar "CANNOSCALEVALUE")) (calculation_text_long_be_dxf_code text))) (angle t1 t2) (+ (/ 0.5 (getvar "CANNOSCALEVALUE")) (calculation_text_height_be_dxf_code text)))
	)
       ( T "Не попадено в точку 2-1 +")
       ); cond
     (cond
       ((equal t10 t1 1)
	(polar (polar t1 (angle t1 t5) (+ (/ 0.5 (getvar "CANNOSCALEVALUE")) (calculation_text_long_be_dxf_code text))) (angle t1 t2) (+ (/ 0.5 (getvar "CANNOSCALEVALUE")) (calculation_text_height_be_dxf_code text)))
	)
       ((equal t10 t2 1)
	(polar (polar t2 (angle t1 t5) (+ (/ 0.5 (getvar "CANNOSCALEVALUE")) (calculation_text_long_be_dxf_code text))) (angle t2 t1) (/ 0.5 (getvar "CANNOSCALEVALUE")))
	)
       ((equal t10 t4 1)
	(polar (polar t4 (angle t5 t1) (/ 0.5 (getvar "CANNOSCALEVALUE"))) (angle t2 t1) (/ 0.5 (getvar "CANNOSCALEVALUE")))
	)
       ((equal t10 t5 1)
	(polar (polar t5 (angle t5 t1) (/ 0.5 (getvar "CANNOSCALEVALUE"))) (angle t1 t2) (+ (/ 0.5 (getvar "CANNOSCALEVALUE")) (calculation_text_height_be_dxf_code text)))
	)
       ( T "Не попадено в точку 2-1 -")
       ); cond
     ); if
   )
  ((= (angle t1 t5) long)
   (if (> d 0)
     (cond
       ((equal t10 t1 1)
	(polar (polar t1 (angle t1 t5) (/ 0.5 (getvar "CANNOSCALEVALUE"))) (angle t1 t2) (/ 0.5 (getvar "CANNOSCALEVALUE")))
	)
       ((equal t10 t2 1)
	(polar (polar t2 (angle t1 t5) (/ 0.5 (getvar "CANNOSCALEVALUE"))) (angle t2 t1) (+ (/ 0.5 (getvar "CANNOSCALEVALUE")) (calculation_text_long_be_dxf_code text)))
	)
       ((equal t10 t4 1)
	(polar (polar t4 (angle t5 t1) (+ (/ 0.5 (getvar "CANNOSCALEVALUE")) (calculation_text_height_be_dxf_code text))) (angle t2 t1) (+ (/ 0.5 (getvar "CANNOSCALEVALUE")) (calculation_text_long_be_dxf_code text)))
	)
       ((equal t10 t5 1)
	(polar (polar t5 (angle t5 t1) (+ (/ 0.5 (getvar "CANNOSCALEVALUE")) (calculation_text_height_be_dxf_code text))) (angle t1 t2) (/ 0.5 (getvar "CANNOSCALEVALUE")))
	)
       ( T "Не попадено в точку 1-5 +")
       ); cond
     (cond
       ((equal t10 t1 1)
	(polar (polar t1 (angle t1 t5) (/ 0.5 (getvar "CANNOSCALEVALUE"))) (angle t1 t2) (+ (/ 0.5 (getvar "CANNOSCALEVALUE")) (calculation_text_long_be_dxf_code text)))
	)
       ((equal t10 t2 1)
	(polar (polar t2 (angle t1 t5) (/ 0.5 (getvar "CANNOSCALEVALUE"))) (angle t2 t1) (/ 0.5 (getvar "CANNOSCALEVALUE")))
	)
       ((equal t10 t4 1)
	(polar (polar t4 (angle t5 t1) (+ (/ 0.5 (getvar "CANNOSCALEVALUE")) (calculation_text_height_be_dxf_code text))) (angle t2 t1) (/ 0.5 (getvar "CANNOSCALEVALUE")))
	)
       ((equal t10 t5 1)
	(polar (polar t5 (angle t5 t1) (+ (/ 0.5 (getvar "CANNOSCALEVALUE")) (calculation_text_height_be_dxf_code text))) (angle t1 t2) (+ (/ 0.5 (getvar "CANNOSCALEVALUE")) (calculation_text_long_be_dxf_code text)))
	)
       ( T "Не попадено в точку 1-5 -")
       ); cond
     ); if
   )
  ((= (angle t5 t1) long)
   (if (> d 0)
     (cond
       ((equal t10 t1 1)
	(setq t11 (polar (polar t1 (angle t1 t5) (+ (/ 0.5 (getvar "CANNOSCALEVALUE")) (calculation_text_height_be_dxf_code text))) (angle t1 t2) (+ (/ 0.5 (getvar "CANNOSCALEVALUE")) (calculation_text_long_be_dxf_code text))))
	)
       ((equal t10 t2 1)
	(setq t11 (polar (polar t2 (angle t1 t5) (+ (/ 0.5 (getvar "CANNOSCALEVALUE")) (calculation_text_height_be_dxf_code text))) (angle t2 t1) (/ 0.5 (getvar "CANNOSCALEVALUE"))))
	)
       ((equal t10 t4 1)
	(setq t11 (polar (polar t4 (angle t5 t1) (/ 0.5 (getvar "CANNOSCALEVALUE"))) (angle t2 t1) (/ 0.5 (getvar "CANNOSCALEVALUE"))))
	)
       ((equal t10 t5 1)
	(setq t11 (polar (polar t5 (angle t5 t1) (/ 0.5 (getvar "CANNOSCALEVALUE"))) (angle t1 t2) (+ (/ 0.5 (getvar "CANNOSCALEVALUE")) (calculation_text_long_be_dxf_code text))))
	)
       ( T "Не попадено в точку 5-1 +")
       ); cond
     (cond
       ((equal t10 t1 1)
	(setq t11 (polar (polar t1 (angle t1 t5) (+ (/ 0.5 (getvar "CANNOSCALEVALUE")) (calculation_text_height_be_dxf_code text))) (angle t1 t2) (/ 0.5 (getvar "CANNOSCALEVALUE"))))
	)
       ((equal t10 t2 1)
	(setq t11 (polar (polar t2 (angle t1 t5) (+ (/ 0.5 (getvar "CANNOSCALEVALUE")) (calculation_text_height_be_dxf_code text))) (angle t2 t1) (+ (/ 0.5 (getvar "CANNOSCALEVALUE")) (calculation_text_long_be_dxf_code text))))
	)
       ((equal t10 t4 1)
	(setq t11 (polar (polar t4 (angle t5 t1) (/ 0.5 (getvar "CANNOSCALEVALUE"))) (angle t2 t1) (+ (/ 0.5 (getvar "CANNOSCALEVALUE")) (calculation_text_long_be_dxf_code text))))
	)
       ((equal t10 t5 1)
	(setq t11 (polar (polar t5 (angle t1 t5) (/ 0.5 (getvar "CANNOSCALEVALUE"))) (angle t1 t2) (/ 0.5 (getvar "CANNOSCALEVALUE"))))
	)
       ( T "Не попадено в точку 5-1 -")
       ); cond
     ); if
   )
  ( T "не сработал угол")
  );cond
  )
