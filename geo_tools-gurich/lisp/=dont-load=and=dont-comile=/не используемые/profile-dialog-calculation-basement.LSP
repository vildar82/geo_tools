(defun profile-dialog-calculation-basement (block-profile-obj / dcl_id profile-string-list)
  (setq dcl_id (load_dialog "Диалоговые окна.dcl"))
  (new_dialog "profile_dialog_calculation_basement" dcl_id)
  (setq profile-string-list(vlax-ldata-get block-profile-obj"profile-string-list"))
  (start_list "list-str")
  (foreach x profile-string-list
    (if (or (eq (nth 1 x)"name-points")(eq (nth 1 x)"elevations")(eq (nth 1 x)"distance")(eq (nth 1 x)"dist-downgrade")(eq (nth 1 x)"map-trace")(eq (nth 1 x)"angle-trace")(eq (nth 1 x)"pikets"))
      (add_list (strcat
		  (car x)
		  (cond
		    ((eq (nth 9 x)"-")
		     "[Нет связи]")
		    ((eq (nth 9 x)"B")
		     "[Связано и заблокировано]")
		    ((eq (type(nth 9 x)) 'VLA-OBJECT)
		     "[Связано]")
		    )
		  (cond
		    ((eq (nth 10 x)"-")
		     "[Нет объектов]")
		    ((eq (type(nth 9 x)) 'LIST)
		     "[Нанесено]")
		    )
		  )
		)
      )
    )
  (end_list)
  (start_dialog)
  (unload_dialog dcl_id)
  )
