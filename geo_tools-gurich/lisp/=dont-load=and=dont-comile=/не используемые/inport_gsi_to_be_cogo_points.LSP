(defun C:inport_gsi_to_be_cogo_points ( / filename file_points_list mode osn putsdr33file sdr33file str x insert-statist no-insert-statist list-str)
  (geo_tools-help "inport_gsi_to_be_cogo_points")
  (load_global_variable)
  (terpri)
  (if
    C3D_active_document
    (progn
      (setq insert-statist 0)
      (setq no-insert-statist 0)
      (setq osn (getvar "OSMODE"))
      (setvar "OSMODE" 0)
      (setq putSDR33file (getfiled "Выбор файла gsi" (getvar "DWGPREFIX") "gsi" 0))
      (setq FileName(vl-string-translate "," "."(substr putSDR33file (+(vl-string-position 92 putSDR33file 0 T)2) (-(strlen putSDR33file)(+(vl-string-position 92 putSDR33file 0 T)2)3))))
      (setq SDR33file (open putSDR33file"r"))
      (setq str (read-line SDR33file))
      (while (not(eq str nil))
	(setq list-str (edit-string-clear-gsi(convert-string-to-list-be-delimiter str " ")))
	(if list-str
	  (setq file_points_list
		 (append file_points_list
			 (list list-str)
			 )))
	(setq str (read-line SDR33file))
	)
      (close SDR33file)
;;;      (princ file_points_list)
;;;      (if file_points_list(file_write_list_to_file(strcat *geo_tools_root_dir* "\\31.txt")file_points_list))
      (if file_points_list
	(progn
	  (setvar "nomutt" 1)
	  (setvar "cmdecho" 0)
	  (if
	    (eq(tblsearch "LAYER" FileName)nil)
	    (command "_-LAYER" "с" FileName "")
	    (command "_-LAYER" "_S" FileName "")
	    )
	  (setvar "cmdecho" 1)
	  (setvar "nomutt" 0)
	  (mapcar '(lambda (x)
		     (if(not(or(eq(nth 1 x)nil)(eq(nth 2 x)nil)(eq(nth 3 x)nil)(eq(nth 0 x)nil)))
		       (if (not (check-point-to-drawning (list (nth 1 x)(nth 2 x)(nth 3 x)(nth 0 x))))
			 (if(not(and (=(nth 1 x)0.0)(=(nth 2 x)0.0)(=(nth 3 x)0.0)))
			   (progn
			     (vlax-put-property(vla-add C3D_points (vlax-3d-point (nth 2 x)(nth 1 x)(nth 3 x)))'Description (nth 0 x))
			     (setq insert-statist (1+ insert-statist))
			     )
			   (setq no-insert-statist (1+ no-insert-statist))
			   )
			 )
		       )
		     )
		  file_points_list)
	  (princ "\nВставлено ")
	  (princ insert-statist)
	  (princ " точек")
	  (princ "\nПропущено ")
	  (princ no-insert-statist)
	  (princ " точек")
	  )
	(alert "В выбраном файле координат не обнаружено!")
	)
      (setvar "OSMODE" osn)
      )
    (alert "Выполнение комманды предполагает ее запуск в AutoCAD Civil 3D!\nТекущий AutoCAD им не является или представляет собой не поддерживаемую(временно?) версию.")
    )
  (princ)
  )
