(defun C:proba1 ( /  LIST-FILES list-filez LIST-NO LIST-POINTS LIST-YES NUMBER N SUMM)
  (setq list-filez(file_read_to_list "d:\\names-files.txt"))
  (setq list-points(file_read_to_list "d:\\names-points.txt"))
  (foreach z list-filez
    (setq list-files (append list-files (list (get-number-if-string z)))))
  (setq n 0)
  (setq summ (itoa(length list-points)))
  (foreach x list-points
    (grtext -1 (strcat"Обрабатываю "(itoa n)"/" summ))
    (bump)
    (if
      (setq number (analysis-number-item-in-list x list-files))
      (progn
	(setq list-yes (append list-yes (list x)))
	(setq list-files (edit-list-del-item-by-number number list-files))
	(while (setq number (analysis-number-item-in-list x list-files))
	  (bump)
	  (setq list-files (edit-list-del-item-by-number number list-files))
	  )
	)
      (setq list-no (append list-no (list x)))
      )
    (setq n (1+ n))
    )
  (file_write_list_to_file "d:\\Сделано.txt" list-yes)
  (file_write_list_to_file "d:\\Не сделано.txt" list-no)
  (file_write_list_to_file "d:\\Остатки.txt" list-files)
  (grtext -1 "")
  (princ)
  )

(defun get-number-if-string (string / flag n result simvol text_list)
  (setq text_list (vl-string->list string))
  (setq n 0)
  (setq flag T)
  (while flag
    (setq simvol (nth n text_list))
    (if
      (wcmatch (chr simvol) "#")
      (setq result (append result (list simvol)))
      (setq flag nil))
    (setq n (1+ n))
    (if (= n (length text_list))(setq flag nil))
    )
  (vl-list->string result)
  )
