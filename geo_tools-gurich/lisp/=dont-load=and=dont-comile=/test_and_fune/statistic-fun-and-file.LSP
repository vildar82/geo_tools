(defun C:statistic-fun-and-file ( / fun length-list pos result-list temp y)
  (foreach x (file_find_be_extension (strcat *geo_tools_root_dir* "\\lisp") "lsp")
    (if (not(or(wcmatch x "*=dont-comile=*")(wcmatch x "*=without-fail-loading=*")(wcmatch x "*not_my*")))
      (progn
	  (setq y (apply 'strcat (file_read_to_list x)))
	  (setq pos 0)
	(setq n 0)
	  (while (wcmatch (substr y (1+ pos)) "*(defun *")
	    (setq n (1+ n))
	    (setq pos (+(vl-string-search "(defun " y pos)(strlen "(defun ")))
	    (setq length-list nil)
	    (foreach z (list "(" ";" " " "\t")
	      (if (setq temp(vl-string-search z (substr y (1+ pos))))
		(setq length-list (append length-list (list temp))))
	      )
	    (if (not(= ""(setq fun(vl-string-trim " \t" (substr y (1+ pos) (apply 'min length-list))))))
	      (progn
		(if (not(=(vl-filename-base x)
			  (setq fun(if (="C:"(substr fun 1 2))
			    (substr fun 3)
			    fun
			    ))))
		  (setq result-list (append result-list (list (strcat "(" (itoa n) ")"(vl-filename-base x) "=>" fun))))
		  )
		)
	      )
	    )
	)
      );if
    (bump)
    )
  (if result-list
    (file_write_list_to_file(strcat *geo_tools_root_dir* "\\lisp\\erorrs-file-name.txt")result-list)
    )
  (princ)
  )
