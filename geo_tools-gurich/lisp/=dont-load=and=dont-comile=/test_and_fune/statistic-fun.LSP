(defun C:statistic-fun ( / fun fun-list fun-list-c length-list lsp-file-list n pos temp text-lsp-file-list y fun-coincidence statistic-fun-list)
  (setq lsp-file-list (file_find_be_extension (strcat *geo_tools_root_dir* "\\lisp") "lsp"))
  (foreach x lsp-file-list
    (if (not(or(wcmatch x "*=dont-comile=*")(wcmatch x "*=without-fail-loading=*")(wcmatch x "*not_my*")))
      (progn
	(setq y (apply 'strcat (file_read_to_list x)))
	(setq text-lsp-file-list (append text-lsp-file-list (list y)))
	(setq pos 0)
	(setq n 0)
	(while (wcmatch (substr y (1+ pos)) "*(defun *")
	  (setq n (1+ n))
	  (setq pos (+(vl-string-search "(defun " y pos)(strlen "(defun ")))
	  (setq length-list nil)
	  (foreach z (list "(" ";" " " "\t")
	    (if (setq temp(vl-string-search z (substr y (1+ pos))))
	      (setq length-list (append length-list (list temp))))
	    )
	  (if (not(= ""(setq fun(vl-string-trim " \t" (substr y (1+ pos) (apply 'min length-list))))))
	    (if (="C:"(substr fun 1 2))
	      (setq fun-list-c (append fun-list-c (list (substr fun 3))))
	      (setq fun-list (append fun-list (list fun)))
	      )
	    )
	  )
	)
      );if
    (bump)
    )
  (setq fun-list(acad_strlsort fun-list))
  (foreach funk fun-list
    (setq fun-coincidence 0)
    (foreach text-lsp-file text-lsp-file-list
      (setq pos 0)
      (while (vl-string-search (strcat "("funk) text-lsp-file pos)
	(setq pos (+(vl-string-search (strcat "("funk) text-lsp-file pos)(strlen (strcat "("funk))))
	(setq fun-coincidence (1+ fun-coincidence))))
    (setq statistic-fun-list (append statistic-fun-list (list (strcat "(" (itoa fun-coincidence) ")"funk))))
    (bump)
    )
  (if fun-list(file_write_list_to_file(strcat *geo_tools_root_dir* "\\lisp\\fun.txt")fun-list))
  (if fun-list-c(file_write_list_to_file(strcat *geo_tools_root_dir* "\\lisp\\fun-c.txt")(acad_strlsort fun-list-c)))
  (if statistic-fun-list(file_write_list_to_file(strcat *geo_tools_root_dir* "\\lisp\\statistic-fun.txt")statistic-fun-list))
  (princ)
  )
