(defun new-xml-and-properties (name-file / attributs attribut o-doc properties puncts squares type-puncts type-punct z-only)
  (setq o-doc (XML-create-blank-file(strcat(getvar "DWGPREFIX")name-file)))
  (setq properties (XML-Add-Child o-doc "properties"))
  (setq attributs (XML-Add-Child properties "attributs"))
  (setq type-puncts (XML-Add-Child properties "type-puncts"))
  (foreach x (list
	       (list "name" "Имя пункта")
	       (list "N" "Северная координата")
	       (list "E" "Восточная координата")
	       (list "Z" "Отметка")
	       (list "type" "Тип пункта")
	       (list "address" "Адрес, местоположение")
	       (list "year" "Год получения сведений")
	       (list "comment" "Коментарий"))
    (setq attribut (XML-Add-Child attributs "attribut"))
    (XML-Add-Attribute attribut "name" (nth 0 x))
    (XML-Add-Attribute attribut "comment" (nth 1 x))
    )
  
  (foreach x (list
	       (list"ст.репер" "МГГТ репер стенной")
	       (list"гор.марка" "МГГТ грунтовые знаки")
	       (list"ПЗ" "МГГТ грунтовые знаки")
	       (list"век.репер" "МГГТ вековой репер")
	       (list"сигнал" "МГГТ сигнал")
	       (list"ст.марка" "МГГТ стенная марка")
	       (list"ст.знак штанга" "МГГТ стенной знак штанга")
	       (list"надстройка" "МГГТ надстройка")
	       (list"пирамида" "МГГТ пирамида")
	       (list"местн.предмет" "МГГТ местный предмет")
	       (list"марка" "МГГТ тип знака не определен")
	       (list"керн" "МГГТ тип знака не определен")
	       (list"рельс" "МГГТ грунтовые знаки")
	       (list"дюбель" "МГГТ тип знака не определен")
	       (list"гвоздь" "МГГТ тип знака не определен"))
    (setq type-punct (XML-Add-Child type-puncts "type-punct"))
    (XML-Add-Attribute type-punct "name" (nth 0 x))
    (XML-Add-Attribute type-punct "block-name" (nth 1 x))
    )
  (setq puncts (XML-Add-Child o-doc "puncts"))
  (setq squares (XML-Add-Child puncts "squares"))
  (setq z-only (XML-Add-Child puncts "z-only"))
  (XML-Save o-doc)
  (list o-doc squares z-only)
  )

(defun C:xml-1 ( / LIST-OBJ N NO-XY-COOR O-DOC ALL CORRENT-LIST-ITEM POINT x y z)
  ;
  (setq list-obj(new-xml-and-properties "Новый каталог координат.xml"))
  (setq o-doc(XML-Get-XMLObject (strcat(getvar "DWGPREFIX")"каталог координат.xml")))
  (setq no-xy-coor(convert-child-to-ass-list (XML-Get-Child-ByAttribute o-doc nil "name" "no-xy-coor")))
;;;  (setq all(convert-child-to-ass-list (XML-Get-Child-ByAttribute o-doc nil "name" "all")))
  (setq n 1)
  (foreach x no-xy-coor
    (if (=(rem n 100)0)(grtext -1 (strcat"Запись "(itoa n)"/" (itoa(length no-xy-coor)))))
    (convert-ass-list-to-punkt-recorg (nth 2 list-obj) x)
    (setq n (1+ n)))
  (XML-Save (nth 0 list-obj))
  (setq all(convert-text-file-to-ass-list (strcat (strcat(getvar "DWGPREFIX"))"all.coor.txt")))
  (setq n 1)
  (foreach y all
    (if (=(rem n 100)0)
      (progn
;;;	(XML-Save (nth 0 list-obj))
	(grtext -1 (strcat"Запись "(itoa n)"/" (itoa(length all))))
	)
      )
    (setq point (list (atof(cadr(assoc"E"y)))(atof(cadr(assoc"N"y)))))
    (setq corrent-list-item (XML-Get-Child-ByAttribute (nth 1 list-obj) nil "name" (analisis-point-square point)))
    (if(not corrent-list-item)
      (progn
	(setq corrent-list-item (XML-Add-Child (nth 1 list-obj) "square"))
	(XML-Add-Attribute corrent-list-item "name" (analisis-point-square point))
	)
      )
    (convert-ass-list-to-punkt-recorg corrent-list-item y)
    (setq n (1+ n))
    )
  (XML-Save (nth 0 list-obj))
  (foreach z (append list-obj (list o-doc))
    (vlax-release-object z))
  (grtext -1 "")
  (princ)
  )



(defun C:xml-3 ( / collection n nn o-doc punkt-recorg squares z-only COMMENT RESULT)
  ;
  (setq o-doc(XML-Get-XMLObject (strcat(getvar "DWGPREFIX")"Новый каталог координат.xml")))
  (setq squares(XML-Get-Child (XML-Get-Child o-doc nil "puncts") nil "squares"))
  (setq z-only(XML-Get-Child (XML-Get-Child o-doc nil "puncts") nil "z-only"))
  (setq n 1)
  (foreach x (XML-Get-ChildList squares)
    (setq nn 0)
    (setq collection (XML-Get-Children x nil))
    (while (setq punkt-recorg (vlax-get-property collection 'item nn))
      (grtext -1 (strcat(itoa n)"/"(itoa nn)"/"(itoa(vlax-get-property collection 'length))))
      (if (setq comment (XML-Get-Attribute punkt-recorg "comment" ""))
	(setq result(append result(list comment)))
	)
      (setq nn (1+ nn))
      )
    (vlax-release-object collection)
    (vlax-release-object x)
    (setq n (1+ n))
    )
  (file_write_list_to_file (strcat(getvar "DWGPREFIX")"raport.txt") result)
  (XML-SaveAs o-doc (strcat(getvar "DWGPREFIX")"Новый каталог координат_.xml"))
  (vlax-release-object o-doc)
  (vlax-release-object squares)
  (vlax-release-object z-only)
  (grtext -1 "")
  (princ)
  )



(defun C:xml-4 ( / collection n nn o-doc punkt-recorg squares z-only)
  ;удаление лишних коментариев "Альт.:; "
  (setq o-doc(XML-Get-XMLObject (strcat(getvar "DWGPREFIX")"Новый каталог координат.xml")))
  (setq squares(XML-Get-Child (XML-Get-Child o-doc nil "puncts") nil "squares"))
  (setq z-only(XML-Get-Child (XML-Get-Child o-doc nil "puncts") nil "z-only"))
  (setq n 1)
  (foreach x (XML-Get-ChildList squares)
    (setq nn 0)
    (setq collection (XML-Get-Children x nil))
    (while (setq punkt-recorg (vlax-get-property collection 'item nn))
      (grtext -1 (strcat(itoa n)"/"(itoa nn)"/"(itoa(vlax-get-property collection 'length))))
      (if (setq comment (XML-Get-Attribute punkt-recorg "comment" ""))
	(if(vl-string-search "Альт.:; " comment)
	  (XML-Put-Attribute punkt-recorg "comment" (vl-string-subst-while comment "Альт.:; "))
	  )
	)
      (setq nn (1+ nn))
      )
    (vlax-release-object collection)
    (vlax-release-object x)
    (setq n (1+ n))
    )
  (XML-SaveAs o-doc (strcat(getvar "DWGPREFIX")"Новый каталог координат_.xml"))
  (grtext -1 "")
  (princ)
  )

  (defun vl-string-subst-while (string str / )
    (while (vl-string-search str string)
      (setq string (vl-string-subst "" str string)))
    string)


;;;(vl-string-subst-while"Альт.:; Альт.: name=25551 N=-3711.320 E=-9728.440 address=Солнцево..(ПЗ); Альт.:; Альт.: name=25551 N=-3711.320 E=-9728.440""Альт.:; ")
