(defun convert-baza-to-xml (/ list-file n name-list result-list)
  (setq list-file(file_read_to_list (strcat *geo_tools_user_dat_dir* "\\data\\baza.dat")))
  (setq name-list(list "vertical-scale" "horizontal-scale" "reference-level" "patch_sh" "name_layout" "shtamp_type" "flag_back_model"))
  (setq n 0)
  (repeat (length list-file)
    (setq result-list(append result-list(list (list
						(nth n name-list)
						(convert-str-be-type
						  (nth n list-file)
						  (cond
						    ((= n 0)
						     "REAL")
						    ((= n 1)
						     "REAL")
						    ((= n 2)
						     "REAL")
						    ((= n 3)
						     "STR")
						    ((= n 4)
						     "STR")
						    ((= n 5)
						     "STR")
						    ((= n 6)
						     "STR")
						    )
						  )))))
    (setq n (1+ n))
    )
  (file_xml_write_be_list (strcat *geo_tools_user_dat_dir* "\\data\\baza.xml")result-list)
  )
