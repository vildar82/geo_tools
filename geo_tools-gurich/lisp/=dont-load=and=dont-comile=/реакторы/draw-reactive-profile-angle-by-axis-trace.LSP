(defun draw-reactive-profile-angle-by-axis-trace (axis-trace-obj start-profile-point /
						  angle-list angle-list-obj angle-point angle-text-obj arrow-angle g model_spece n temp text_str)
  (setq model_spece (vla-get-ModelSpace (vla-get-ActiveDocument (vlax-get-acad-object))))
  (setq angle-list(analisis-ang-rotate-for-lwpoly axis-trace-obj))
  (setq n 0)
  (repeat (length angle-list)
    (setq g (nth n angle-list))
    (if (not (and (< (- pi (/ pi 180)) g) (< g (+ pi (/ pi 180)))))
      (progn
	(setq angle-point (list (+(nth 0 start-profile-point)(vlax-curve-getDistAtParam axis-trace-obj (1+ n))) (-(nth 1 start-profile-point)15)))
	(setq text_str (strcat (rtos (/ (if (> g pi) (- (* pi 2) g) g) (/ pi 180)) 2 0) "%%d "))
	(setq angle-text-obj (vla-AddText model_spece text_str (vlax-3D-point angle-point) 2.5))
	(vla-put-Alignment angle-text-obj 11)
	(vla-put-TextAlignmentPoint angle-text-obj (vlax-3D-point angle-point))
	(vla-put-Rotation angle-text-obj 0)
	(vla-put-Linetype angle-text-obj "Continuous")
	(setq angle-list-obj (append angle-list-obj (list angle-text-obj)))
	(setq temp (list (mapcar '+ angle-point '(0.0 2.0))angle-point(mapcar '- angle-point '(0.0 2.0))))
	(setq temp (apply 'append (mapcar 'list (mapcar 'car temp)(mapcar 'cadr temp))))
	(setq arrow-angle (vla-addLightWeightPolyline model_spece
			    (vlax-make-variant(vlax-safearray-fill
						(vlax-make-safearray vlax-vbDouble '(0 . 5))
						temp))))
	(setq angle-list-obj (append angle-list-obj (list arrow-angle)))
	(cond
	  ((< g pi)
	   (princ "\n Лево")
	   (vla-setWidth arrow-angle 0 0.0 1.0)
	   )
	  ((> g pi)
	   (princ "\n Право")
	   (vla-setWidth arrow-angle 1 1.0 0.0)
	   )
	  )
	)
      )
    (setq n (1+ n))
    )
  angle-list-obj
  )
