(defun C:txt_to_poly_4_point (/ flag list-points n p1 p2 p3 p4 put-text-file raw-list-string)
  (if(setq put-text-file (getfiled "Выбор файла" (getvar "DWGPREFIX") "txt" 0))
    (progn
      (setq raw-list-string (file_read_to_list put-text-file))
      (foreach x raw-list-string
	(setq temp (convert-string-to-list-be-delimiter x ","))
	(setq list-points(append list-points(list(list(atof(nth 2 temp))(atof(nth 1 temp))))))
	)
      (setq n 0)
      (while (not flag)
	(setq p1 (nth n list-points))
	(setq p2 (nth (+ n 1) list-points))
	(setq p3 (nth (+ n 2) list-points))
	(setq p4 (nth (+ n 3) list-points))
	(if (and p1 p2 p3 p4)
	  (draw-lwpolyline-vla-by-list-property
	    (list(cons "spece" (if (eq (getvar "CTAB")"Model")model_spece paper_spece))
		 (cons "Coordinates" (list p1 p2 p3 p4))
		 (cons "Closed" -1)
		 ))
	  (setq flag T)
	  )
	(setq n (+ n 4))
	)
      )
    )
  (princ)
  )
