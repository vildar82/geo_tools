(defun C:txt_to_poly_delimiter_1 (/ list-points p1 p2 put-text-file temp raw-list-string)
  (if(setq put-text-file (getfiled "Выбор файла" (getvar "DWGPREFIX") "txt" 0))
    (progn
      (setq raw-list-string (file_read_to_list put-text-file))
      (foreach x raw-list-string
	(setq temp (convert-string-to-list-be-delimiter x ","))
	(setq list-points(append list-points(list(list(atof(nth 2 temp))(atof(nth 1 temp))(atoi(nth 4 temp))))))
	)
      (setq point (nth 0 list-points-poly))
      (setq list-points-poly (append list-points-poly (list (list(nth 0 point)(nth 1 point)))))
      (setq n 1)
      (while (not flag)
	(setq point (nth n list-points))
	(if (= (nth 2 point) 1)
	  (progn
	    (if (> (length list-points-poly) 2)
	      (draw-lwpolyline-vla-by-list-property
		(list(cons "spece" (if (eq (getvar "CTAB")"Model")model_spece paper_spece))
		     (cons "Coordinates" list-points-poly)
		     (cons "Closed" -1)
		     )
		)
	      (princ (strcat "\nГраница не построена!Мало точек: " (itoa(length list-points-poly)) " шт., кончилась на "(itoa (1+ n))" строке файла!"))
	      )
	    (setq list-points-poly nil)
	    )
	  (setq list-points-poly (append list-points-poly (list (list(nth 0 point)(nth 1 point)))))
	  )
	(setq n (1+ n))
	)
      (repeat (1-(length list-points))
	(setq p1 (car list-points))
	(setq list-points (cdr list-points))
	(setq p2 (car list-points))
	(if (and p1 p2)
	  (draw-lwpolyline-vla-by-list-property
	    (list(cons "spece" (if (eq (getvar "CTAB")"Model")model_spece paper_spece))
		 (cons "Coordinates" (list p1 p2))
		 )
	    )
	  )
	)
      )
    )
  (princ)
  )
