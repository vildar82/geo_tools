(defun C:txt_to_poly_delimiter_1 (/ flag list-points list-points-poly n point put-text-file raw-list-string temp)
  (if(setq put-text-file (getfiled "Выбор файла" (getvar "DWGPREFIX") "txt" 0))
    (progn
      (setq raw-list-string (file_read_to_list put-text-file))
      (foreach x raw-list-string
	(setq temp (convert-string-to-list-be-delimiter x ","))
	(setq list-points(append list-points(list(list(atof(nth 2 temp))(atof(nth 1 temp))(atoi(nth 4 temp))))))
	)
      (setq point (nth 0 list-points))
      (setq list-points-poly (list(list(nth 0 point)(nth 1 point))))
      (setq n 1)
      (while (not flag)
	(setq point (nth n list-points))
	(if (or(= point nil)(= (nth 2 point) 1))
	  (progn
	    (if (> (length list-points-poly) 2)
	      (draw-lwpolyline-vla-by-list-property
		(list(cons "spece" (if (eq (getvar "CTAB")"Model")model_spece paper_spece))
		     (cons "Coordinates" list-points-poly)
		     (cons "Closed" -1)
		     )
		)
	      (princ (strcat "\nГраница не построена!Мало точек: " (itoa(length list-points-poly)) " шт., кончилась на "(itoa n)" строке файла!"))
	      )
	    (if (= point nil) (setq flag T)(setq list-points-poly (list(list(nth 0 point)(nth 1 point)))))
	    )
	  (setq list-points-poly (append list-points-poly (list (list(nth 0 point)(nth 1 point)))))
	  )
	(setq n (1+ n))
	)
      )
    )
  (princ)
  )
