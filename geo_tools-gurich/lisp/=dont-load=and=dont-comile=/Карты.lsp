(defun C:run ( / list_directory new_directoryes new_files list_files koren)
  (setq koren "d:\\Карты")
  (setq list_directory (list koren))
  (while (not(eq list_directory nil))
    (setq new_directoryes (cddr(vl-directory-files (car list_directory) nil -1)))
    (setq new_files (vl-directory-files (car list_directory) nil 1))
    (if new_files (setq list_files(append list_files (file-add-patch-to-name-file new_files(car list_directory)))))
    (if new_directoryes (setq list_directory(append list_directory (file-add-patch-to-name-file new_directoryes(car list_directory)))))
    (setq list_directory(cdr list_directory))
    )
  (if list_files (list->file list_files (strcat koren "\\файлы в каталоге.txt")))
  (progn)
  )

(defun list_files_in_dir (koren / list_directory new_directoryes new_files list_files)
  (setq list_directory (list koren))
  (while (not(eq list_directory nil))
    (setq new_directoryes (cddr(vl-directory-files (car list_directory) nil -1)))
    (setq new_files (vl-directory-files (car list_directory) nil 1))
    (if new_files (setq list_files(append list_files (file-add-patch-to-name-file new_files(car list_directory)))))
    (if new_directoryes (setq list_directory(append list_directory (file-add-patch-to-name-file new_directoryes(car list_directory)))))
    (setq list_directory(cdr list_directory))
    )
  list_files
  )


(defun list->file (list_files patch / file)
  (setq file (open patch "w"))
  (repeat (length list_files)
    (write-line (car list_files) file)
    (setq list_files (cdr list_files)))
  (close file)
  )

(defun C:proba ( / str str_list cod1 cod2 cod2+ cod3 cod4 cod5 point)
  (initget)(setq str (getstring "\nВведи: "))
  (setq str_list (vl-string->list str))
  (setq cod1 (code1 (car str_list)))
  (setq str_list (cddr str_list))
  
  (while (not(or(eq (car str_list) (ascii "-"))(eq (car str_list) (ascii ","))(eq (car str_list) nil)))
    (setq cod2 (append cod2 (list(car str_list))))
    (setq str_list (cdr str_list))
    )
  
  (setq cod2 (atof(vl-list->string cod2)))
  (setq cod2 (code2 cod2))
  (if (eq (car str_list) (ascii ","))
    (progn
      (setq str_list (cdr str_list))
      
      (while (not(or(eq (car str_list) (ascii ","))(eq (car str_list) nil)))
	(setq cod2+ (append cod2+ (list(car str_list))))
	(setq str_list (cdr str_list))
	)
      (setq cod2+ (atof(vl-list->string cod2+)))
      (setq cod2+ (code2 cod2+))
  (setq str_list (cdr str_list))
      
      (while (not(eq(car str_list)nil))
	(setq cod2+ nil)
	(while(not(or(eq (car str_list) (ascii ","))
		     (eq (car str_list) nil)))
	  (setq cod2+ (append cod2+ (list(car str_list))))
	  (setq str_list (cdr str_list))
	  )
	(setq cod2 (plus_planshet cod2 (code2(atoi(vl-list->string cod2+)))))
	(setq str_list (cdr str_list))
	)
      ))
      
  (if str_list
    (cond
      ((wcmatch (chr(car str_list)) "[АБВГ]")
       (setq cod3 (code3_500 (chr(car str_list))))
       (setq point (mapcar '+ (list (-(* cod2 6)6)(-(* cod1 4)4)) cod3))
       (setq NI (mapcar '+ point (list 3 2)))
       (setq NW (mapcar '+ point (list 0 2)))
       (setq SI (mapcar '+ point (list 3 0)))
       (setq SW point)
       (draw_trap NW NI SI SW str)
       )
      ((wcmatch (chr(car str_list)) "[XVI]")
       (while (not(or(eq (car str_list) (ascii "-"))(eq (car str_list) nil)))
	 (setq cod3 (append cod3 (list(car str_list))))
	 (setq str_list (cdr str_list))
	 )
       (setq cod3 (vl-list->string cod3))
       (setq cod3 (code3_200 cod3))
       (setq point (mapcar '+ (list (-(* cod2 6)6)(-(* cod1 4)4)) cod3))
       (setq NI (mapcar '+ point (list 1 (gms->dec 0 40 0))))
       (setq NW (mapcar '+ point (list 0 (gms->dec 0 40 0))))
       (setq SI (mapcar '+ point (list 1 0)))
       (setq SW point)
       (draw_trap NW NI SI SW str)
       )
      ((wcmatch (chr(car str_list)) "#")
       (while (not(or(eq (car str_list) (ascii "-"))(eq (car str_list) nil)))
	 (setq cod3 (append cod3 (list(car str_list))))
	 (setq str_list (cdr str_list))
	 )
       (setq cod3 (atof(vl-list->string cod3)))
       (setq cod3 (code3_100 cod3))
       (setq point (mapcar '+ (list (-(* cod2 6)6)(-(* cod1 4)4)) cod3))
       (if str_list
	 (progn
	   (setq str_list (cdr str_list))
	   (while (not(or(eq (car str_list) (ascii "-"))(eq (car str_list) nil)))
	     (setq cod4 (append cod4 (list(car str_list))))
	     (setq str_list (cdr str_list))
	     )
	   (setq cod4 (vl-list->string cod4))
	   (setq cod4 (code4 cod4))
	   (setq point (mapcar '+ point cod4))
	   (if str_list
	     (progn
	       (setq str_list (cdr str_list))
	       (while (not(or(eq (car str_list) (ascii "-"))(eq (car str_list) nil)))
		 (setq cod5 (append cod5 (list(car str_list))))
		 (setq str_list (cdr str_list))
		 )
	       (setq cod5 (vl-list->string cod5))
	       (setq cod5 (code5 cod5))
	       (setq point (mapcar '+ point cod5))
	       (setq NI (mapcar '+ point (list (gms->dec 0 7 30) (gms->dec 0 5 0))))
	       (setq NW (mapcar '+ point (list 0 (gms->dec 0 5 0))))
	       (setq SI (mapcar '+ point (list (gms->dec 0 7 30) 0)))
	       (setq SW point)
	       (draw_trap NW NI SI SW str)
	       )
	     (progn
	       (setq NI (mapcar '+ point (list (gms->dec 0 15 0) (gms->dec 0 10 0))))
	       (setq NW (mapcar '+ point (list 0 (gms->dec 0 10 0))))
	       (setq SI (mapcar '+ point (list (gms->dec 0 15 0) 0)))
	       (setq SW point)
	       (draw_trap NW NI SI SW str)
	       )
	     )
	   )
	 (progn
	   (setq NI (mapcar '+ point (list (gms->dec 0 30 0) (gms->dec 0 20 0))))
	   (setq NW (mapcar '+ point (list 0 (gms->dec 0 20 0))))
	   (setq SI (mapcar '+ point (list (gms->dec 0 30 0) 0)))
	   (setq SW point)
	   (draw_trap NW NI SI SW str)
	   )
	 )
       )
      )
    (progn
      (setq point (list (-(* cod2 6)6)(-(* cod1 4)4)))
      (setq NI (mapcar '+ point (list 6 4)))
      (setq NW (mapcar '+ point (list 0 4)))
      (setq SI (mapcar '+ point (list 6 0)))
      (setq SW point)
      (draw_trap NW NI SI SW str)
      )
    )
  (princ)
  );defun

(defun code4 (c4 /)
  (cond
    ((eq c4 "А")
     (list 0 (gms->dec 0 10 0)))
    ((eq c4 "Б")
     (list (gms->dec 0 15 0) (gms->dec 0 10 0)))
    ((eq c4 "В")
     (list 0 0))
    ((eq c4 "Г")
     (list (gms->dec 0 15 0) 0))))

(defun code5 (c5 /)
  (cond
    ((eq c5 "а")
     (list 0 (gms->dec 0 5 0)))
    ((eq c5 "б")
     (list (gms->dec 0 7 30) (gms->dec 0 5 0)))
    ((eq c5 "в")
     (list 0 0))
    ((eq c5 "г")
     (list (gms->dec 0 7 30) 0))))

      (princ (strcat "\n планшет " str " Масштаб 1:1 000 000"))
      (princ "\n СВ угол рамки\n Д ")
      (princ(dec->gms(nth 0 NI)))(princ "\n Ш ")
      (princ(dec->gms(nth 1 NI)))
      (princ "\n СЗ угол рамки\n Д ")
      (princ(dec->gms(nth 0 NW)))(princ "\n Ш ")
      (princ(dec->gms(nth 1 NW)))
      (princ "\n ЮВ угол рамки\n Д ")
      (princ(dec->gms(nth 0 SI)))(princ "\n Ш ")
      (princ(dec->gms(nth 1 SI)))
      (princ "\n ЮЗ угол рамки\n Д ")
      (princ(dec->gms(nth 0 SW)))(princ "\n Ш ")
      (princ(dec->gms(nth 1 SW)))

(defun code3_200 (c3 / _list n cod str rad)
  (setq _list
	 (list
	   '(1 "I")	   '(2 "II")
	   '(3 "III")	   '(4 "IV")
	   '(5 "V")	   '(6 "VI")
	   '(7 "VII")	   '(8 "VIII")
	   '(9 "IX")	   '(10 "X")
	   '(11 "XI")	   '(12 "XII")
	   '(13 "XIII")	   '(14 "XIV")
	   '(15 "XV")	   '(16 "XVI")
	   '(17 "XVII")	   '(18 "XVIII")
	   '(19 "XIX")	   '(20 "XX")
	   '(21 "XXI")	   '(22 "XXII")
	   '(23 "XXIII")   '(24 "XXIV")
	   '(25 "XXV")	   '(26 "XXVI")
	   '(27 "XXVII")   '(28 "XXVIII")
	   '(29 "XXIX")	   '(30 "XXX")
	   '(31 "XXXI")	   '(32 "XXXII")
	   '(33 "XXXIII")  '(34 "XXXIV")
	   '(35 "XXXV")	   '(36 "XXXVI")))
  (setq n 0)
  (while (not(eq n (length _list)))
    (if (eq c3 (cadr(nth n _list)))
      (progn
	(setq cod (car(nth n _list)))
	(setq n (length _list)))
      (setq n (1+ n))
      )
    )
  (setq str (- 5(fix(/ cod 6))))
  (if (eq (rem cod 6) 0)(setq str (1+ str)))
  (setq rad (-(rem cod 6)1))
  (if (eq rad -1)(setq rad 5))
  (list (* rad 1)(* str (gms->dec 0 40 0)))
  )

(defun code3_500 (c3 /)
  (cond
    ((eq c3 "А")
     '(0 2))
    ((eq c3 "Б")
     '(3 2))
    ((eq c3 "В")
     '(0 0))
    ((eq c3 "Г")
     '(3 0))))


(defun code3_100 (cod / str rad)
  (setq str (- 11(fix(/ cod 12))))
  (if (eq (rem cod 12) 0)(setq str (1+ str)))
  (setq rad (-(rem cod 12)1))
  (if (eq rad -1)(setq rad 11))
  (list (* rad (gms->dec 0 30 0))(* str (gms->dec 0 20 0)))
  )


(defun code1 (bukva / _list n cod)
  (setq _list
	 (list
	   '("A" "a" 1)    '("B" "b" 2)    '("C" "c" 3)    '("D" "d" 4)
	   '("E" "e" 5)    '("F" "f" 6)    '("G" "g" 7)    '("H" "h" 8)
	   '("I" "i" 9)    '("J" "j" 10)    '("K" "k" 11)    '("L" "l" 12)
	   '("M" "m" 13)    '("N" "n" 14)    '("O" "o" 15)    '("P" "p" 16)
	   '("Q" "q" 17)    '("R" "r" 18)    '("S" "s" 19)    '("T" "t" 20)
	   '("U" "u" 21)    '("V" "v" 22)    '("W" "w" 23)    '("Y" "y" 24)))
  (setq n 0)
  (while (not(eq n (length _list)))
    (if (or (eq (chr bukva) (car(nth n _list)))(eq (chr bukva) (cadr(nth n _list))))
      (progn
	(setq cod (caddr(nth n _list)))
	(setq n (length _list)))
      (setq n (1+ n))
      )
    )
  cod
  )

(defun code2 (chislo /)
  (if (< 0 (- chislo 30))
    (- chislo 30)
    chislo)
  )

(defun draw_trap (p1 p2 p3 p4 str / )
  (entmake (list '(0 . "LWPOLYLINE") '(100 . "AcDbEntity") '(6 . "Continuous") '(100 . "AcDbPolyline")
		 '(90 . 8) '(70 . 1) '(43 . 0)
		 (cons 10 p1)
		 (cons 10 p2)
		 (cons 10 p3)
		 (cons 10 p4)
		 (cons 10 p2)
		 (cons 10 p1)
		 (cons 10 p3)
		 (cons 10 p4)
		 ))
  
(entmake (list '(0 . "TEXT")
		 (cons 10 p1)
		 '(72 . 0) '(73 . 1)
		 (cons 11 p1)
		 (cons 40 (/(distance p1 p4)20))
		 (cons 1 (dec->gms(nth 1 p1)))
		 (cons 50 0)
		 (cons 7 (getvar "TEXTSTYLE"))))
  (entmake (list '(0 . "TEXT")
		 (cons 10 p1)
		 '(72 . 2) '(73 . 1)
		 (cons 11 p1)
		 (cons 40 (/(distance p1 p4)20))
		 (cons 1 (dec->gms(nth 0 p1)))
		 (cons 50 (/ pi 2))
		 (cons 7 (getvar "TEXTSTYLE"))))

  (entmake (list '(0 . "TEXT")
		 (cons 10 p2)
		 '(72 . 2) '(73 . 1)
		 (cons 11 p2)
		 (cons 40 (/(distance p1 p4)20))
		 (cons 1 (dec->gms(nth 1 p2)))
		 (cons 50 0)
		 (cons 7 (getvar "TEXTSTYLE"))))
  (entmake (list '(0 . "TEXT")
		 (cons 10 p2)
		 '(72 . 2) '(73 . 3)
		 (cons 11 p2)
		 (cons 40 (/(distance p1 p4)20))
		 (cons 1 (dec->gms(nth 0 p2)))
		 (cons 50 (/ pi 2))
		 (cons 7 (getvar "TEXTSTYLE"))))

    (entmake (list '(0 . "TEXT")
		 (cons 10 p3)
		 '(72 . 2) '(73 . 3)
		 (cons 11 p3)
		 (cons 40 (/(distance p1 p4)20))
		 (cons 1 (dec->gms(nth 1 p3)))
		 (cons 50 0)
		 (cons 7 (getvar "TEXTSTYLE"))))
  (entmake (list '(0 . "TEXT")
		 (cons 10 p3)
		 '(72 . 0) '(73 . 3)
		 (cons 11 p3)
		 (cons 40 (/(distance p1 p4)20))
		 (cons 1 (dec->gms(nth 0 p3)))
		 (cons 50 (/ pi 2))
		 (cons 7 (getvar "TEXTSTYLE"))))
  
  (entmake (list '(0 . "TEXT")
		 (cons 10 p4)
		 '(72 . 0) '(73 . 3)
		 (cons 11 p4)
		 (cons 40 (/(distance p1 p4)20))
		 (cons 1 (dec->gms(nth 1 p4)))
		 (cons 50 0)
		 (cons 7 (getvar "TEXTSTYLE"))))
  (entmake (list '(0 . "TEXT")
		 (cons 10 p4)
		 '(72 . 0) '(73 . 1)
		 (cons 11 p4)
		 (cons 40 (/(distance p1 p4)20))
		 (cons 1 (dec->gms(nth 0 p4)))
		 (cons 50 (/ pi 2))
		 (cons 7 (getvar "TEXTSTYLE"))))
  
  (entmake (list '(0 . "TEXT")
		 (cons 10 p4)
		 '(72 . 4) '(73 . 0)
		 (cons 11 (mapcar'+ p4(list(/(distance p1 p2)2)(/(distance p1 p4)2))))
		 (cons 40 (/(distance p1 p4)8))
		 (cons 1 str)
		 (cons 50 0)
		 (cons 7 (getvar "TEXTSTYLE"))))
  
  )




(defun C:ru_100 ( / list_files x file_dir file_name file_ext file_name_list cod1 cod2 cod3 new_file_name)
  (setq list_files (list_files_in_dir "d:\\100k"))
  (mapcar '(lambda (x)
	     (setq cod1 nil cod2 nil)
	     (setq file_dir (vl-filename-directory x))
	     (setq file_name (vl-filename-base x))
	     (setq file_ext (vl-filename-extension x))
	     (setq file_name_list (vl-string->list file_name))
	     (setq cod1 (car file_name_list))
	     (setq file_name_list (cddr file_name_list))
	     
	     (while (not(or(eq (car file_name_list) (ascii "-"))(eq (car file_name_list) (ascii "_"))(eq (car file_name_list) nil)))
	       (setq cod2 (append cod2 (list(car file_name_list))))
	       (setq file_name_list (cdr file_name_list))
	       )
	     (setq cod2 (atof(vl-list->string cod2)))
	     (setq new_file_name (strcat (vl-list->string (list cod1)) "-" (rtos cod2 2 0) "-"))
	     (setq file_name_list (cdr file_name_list))
	     
	     (while (not(eq(car file_name_list)nil))
	       (setq cod3 nil)
	       (while(not(or(eq (car file_name_list) (ascii ","))(eq (car file_name_list) (ascii "-"))(eq (car file_name_list) (ascii "_"))(eq (car file_name_list) nil)))
		 (setq cod3 (append cod3 (list(car file_name_list))))
		 (setq file_name_list (cdr file_name_list))
		 )
	       (setq new_file_name (strcat new_file_name (itoa(atoi(vl-list->string cod3)))(if file_name_list "," "")))
	       (setq file_name_list (cdr file_name_list))
	       )
	     (vl-file-rename x (strcat file_dir "\\" new_file_name file_ext))
	     )
	  list_files)
  (princ)
  )
(defun C:ru_200 ( / list_files x file_dir file_name file_ext file_name_list cod1 cod2 cod3 new_file_name)
  (setq list_files (list_files_in_dir "d:\\200k"))
  (mapcar '(lambda (x)
	     (setq cod1 nil cod2 nil)
	     (setq file_dir (vl-filename-directory x))
	     (setq file_name (vl-filename-base x))
	     (setq file_ext (vl-filename-extension x))
	     (setq file_name_list (vl-string->list file_name))
	     (setq cod1 (car file_name_list))
	     (setq file_name_list (cddr file_name_list))
	     
	     (while (not(or(eq (car file_name_list) (ascii "-"))(eq (car file_name_list) (ascii "_"))(eq (car file_name_list) nil)))
	       (setq cod2 (append cod2 (list(car file_name_list))))
	       (setq file_name_list (cdr file_name_list))
	       )
	     (setq cod2 (atof(vl-list->string cod2)))
	     (setq new_file_name (strcat (vl-list->string (list cod1)) "-" (rtos cod2 2 0) "-"))
	     (setq file_name_list (cdr file_name_list))
	     
	     (while (not(eq(car file_name_list)nil))
	       (setq cod3 nil)
	       (while(not(or(eq (car file_name_list) (ascii ","))(eq (car file_name_list) (ascii "-"))(eq (car file_name_list) (ascii "_"))(eq (car file_name_list) nil)))
		 (setq cod3 (append cod3 (list(car file_name_list))))
		 (setq file_name_list (cdr file_name_list))
		 )
	       (setq new_file_name (strcat new_file_name (arab->rim(vl-list->string cod3))(if file_name_list "," "")))
	       (setq file_name_list (cdr file_name_list))
	       )
	     (vl-file-rename x (strcat file_dir "\\" new_file_name file_ext))
	     )
	  list_files)
  (princ)
  )
(defun C:ru_500 ( / list_files x file_dir file_name file_ext file_name_list cod1 cod2 cod3 new_file_name)
  (setq list_files (list_files_in_dir "d:\\500k"))
  (mapcar '(lambda (x)
	     (setq cod1 nil cod2 nil)
	     (setq file_dir (vl-filename-directory x))
	     (setq file_name (vl-filename-base x))
	     (setq file_ext (vl-filename-extension x))
	     (setq file_name_list (vl-string->list file_name))
	     (setq cod1 (car file_name_list))
	     (setq file_name_list (cddr file_name_list))
	     
	     (while (not(or(eq (car file_name_list) (ascii "-"))(eq (car file_name_list) nil)))
	       (setq cod2 (append cod2 (list(car file_name_list))))
	       (setq file_name_list (cdr file_name_list))
	       )
	     (setq cod2 (atof(vl-list->string cod2)))
	     (setq new_file_name (strcat (vl-list->string (list cod1)) "-" (rtos cod2 2 0) "-"))
	     (setq file_name_list (cdr file_name_list))
	     
	     (while (not(eq(car file_name_list)nil))
	       (setq cod3 nil)
	       (while(not(or(eq (car file_name_list) (ascii ","))
			    (eq (car file_name_list) (ascii "-"))
			    (eq (car file_name_list) (ascii "_"))
			    (eq (car file_name_list) nil)))
		 (setq cod3 (append cod3 (list(car file_name_list))))
		 (setq file_name_list (cdr file_name_list))
		 )
	       (setq new_file_name (strcat new_file_name (tr_ABVG(vl-list->string cod3))(if file_name_list "," ""))))
	       (setq file_name_list (cdr file_name_list))
	     (vl-file-rename x (strcat file_dir "\\" new_file_name file_ext))
	       )
	  list_files)
  (princ)
  )

(defun C:ru_50 ( / list_files x file_dir file_name file_ext file_name_list cod1 cod2 cod3 cod4 new_file_name)
  (setq list_files (list_files_in_dir "d:\\50k"))
  
  (mapcar '(lambda (x)
	     (setq cod1 nil cod2 nil cod3 nil)
	     (setq file_dir (vl-filename-directory x))
	     (setq file_name (vl-filename-base x))
	     (setq file_ext (vl-filename-extension x))
	     (setq file_name_list (vl-string->list file_name))
	     (setq cod1 (car file_name_list))
	     (setq file_name_list (cddr file_name_list))
	     
	     (while (not(or(eq (car file_name_list) (ascii "-"))(eq (car file_name_list) nil)))
	       (setq cod2 (append cod2 (list(car file_name_list))))
	       (setq file_name_list (cdr file_name_list))
	       )
	     (setq cod2 (atof(vl-list->string cod2)))
	     (setq new_file_name (strcat (vl-list->string (list cod1)) "-" (rtos cod2 2 0) "-"))
	     (setq file_name_list (cdr file_name_list))
	     
	       (while(not(or(eq (car file_name_list) (ascii ","))
			    (eq (car file_name_list) (ascii "-"))
			    (eq (car file_name_list) nil)))
		 (setq cod3 (append cod3 (list(car file_name_list))))
		 (setq file_name_list (cdr file_name_list))
		 )
	       (setq new_file_name (strcat new_file_name (itoa(atoi(vl-list->string cod3)))"-"))
	       (setq file_name_list (cdr file_name_list))
	     
	     (while (not(eq(car file_name_list)nil))
	       (setq cod4 nil)
	       (while(not(or(eq (car file_name_list) (ascii ","))
			    (eq (car file_name_list) (ascii "-"))
			    (eq (car file_name_list) (ascii "_"))
			    (eq (car file_name_list) nil)))
		 (setq cod4 (append cod4 (list(car file_name_list))))
		 (setq file_name_list (cdr file_name_list))
		 )
	       (setq new_file_name (strcat new_file_name (tr_ABVG(vl-list->string cod4))(if file_name_list "," "")))
	       (setq file_name_list (cdr file_name_list))
	       )
	     (vl-file-rename x (strcat file_dir "\\" new_file_name file_ext))
	     )
	  list_files)
  (princ)
  )

(defun tr_ABVG (c4 /)
  (cond
    ((or(eq c4 "A")(eq c4 "А")(eq c4 "1"))
     "А")
    ((or(eq c4 "B")(eq c4 "Б")(eq c4 "2"))
     "Б")
    ((or(eq c4 "V")(eq c4 "C")(eq c4 "В")(eq c4 "3"))
     "В")
    ((or(eq c4 "G")(eq c4 "D")(eq c4 "Г")(eq c4 "4"))
     "Г")))

(defun arab->rim (arab / n _list result)
  (setq _list
	 (list
	   '(1 "I")	   '(2 "II")
	   '(3 "III")	   '(4 "IV")
	   '(5 "V")	   '(6 "VI")
	   '(7 "VII")	   '(8 "VIII")
	   '(9 "IX")	   '(10 "X")
	   '(11 "XI")	   '(12 "XII")
	   '(13 "XIII")	   '(14 "XIV")
	   '(15 "XV")	   '(16 "XVI")
	   '(17 "XVII")	   '(18 "XVIII")
	   '(19 "XIX")	   '(20 "XX")
	   '(21 "XXI")	   '(22 "XXII")
	   '(23 "XXIII")   '(24 "XXIV")
	   '(25 "XXV")	   '(26 "XXVI")
	   '(27 "XXVII")   '(28 "XXVIII")
	   '(29 "XXIX")	   '(30 "XXX")
	   '(31 "XXXI")	   '(32 "XXXII")
	   '(33 "XXXIII")  '(34 "XXXIV")
	   '(35 "XXXV")	   '(36 "XXXVI")))
  (setq n 0)
  (while (not(eq n (length _list)))
    (if (or (eq arab (cadr(nth n _list)))(eq (atof arab) (car(nth n _list))))
      (progn
	(setq result (cadr(nth n _list)))
	(setq n (length _list)))
      (setq n (1+ n))
      )
    )
  result
  )
